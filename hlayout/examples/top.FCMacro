# FreeCAD 3D view of UNTITLED  (cell TOP)
# Generated by HLayout -- run inside FreeCAD: Macro > Macros... > Execute,
# or  freecadcmd this_file.FCMacro
import FreeCAD as App
import Part
from functools import reduce
try:
    import FreeCADGui
    _GUI = True
except Exception:
    _GUI = False

V = App.Vector
_doc = App.newDocument('UNTITLED_TOP')


def _poly(points):
    return Part.makePolygon(points)


def _fuse(solids):
    solids = [s for s in solids if s is not None and not s.isNull()]
    if not solids:
        return None
    return reduce(lambda a, b: a.fuse(b), solids[1:], solids[0]) if len(solids) > 1 else solids[0]


def _add(name, shape, rgb):
    if shape is None:
        return None
    o = _doc.addObject("Part::Feature", name)
    o.Shape = shape
    if _GUI and o.ViewObject is not None:
        o.ViewObject.ShapeColor = rgb
    return o


def _bondwire(p0, apex, p1, radius):
    """A swept loop p0 -> apex -> p1; falls back to a thin box path."""
    try:
        c = Part.BSplineCurve()
        c.interpolate([p0, apex, p1])
        spine = Part.Wire(c.toShape())
        prof = Part.Wire(Part.makeCircle(radius, p0, apex.sub(p0)))
        return spine.makePipeShell([prof], True, True)
    except Exception:
        legs = []
        for a, b in ((p0, apex), (apex, p1)):
            d = b.sub(a)
            L = d.Length
            if L > 1e-6:
                legs.append(Part.makeCylinder(radius, L, a, d))
        legs.append(Part.makeSphere(radius, apex))
        return _fuse(legs)


# --- layer 3 (1st Routing Conductor) : z 0.0000..0.0120 mm ---
_s = []
_s.append(Part.Face([_poly([V(8.24000,4.10000,0.00000),V(9.24000,4.10000,0.00000),V(9.24000,3.60000,0.00000),V(8.24000,3.60000,0.00000),V(8.24000,4.10000,0.00000)])]).extrude(V(0,0,0.01200)))
_s.append(Part.Face([_poly([V(10.78000,4.10000,0.00000),V(11.25000,4.10000,0.00000),V(11.25000,8.20000,0.00000),V(10.10000,8.20000,0.00000),V(9.00000,8.20000,0.00000),V(9.00000,9.90000,0.00000),V(12.40000,9.90000,0.00000),V(12.40000,8.20000,0.00000),V(11.55000,8.20000,0.00000),V(11.55000,4.10000,0.00000),V(11.78000,4.10000,0.00000),V(11.78000,3.60000,0.00000),V(10.78000,3.60000,0.00000),V(10.78000,4.10000,0.00000)])]).extrude(V(0,0,0.01200)))
_s.append(Part.Face([_poly([V(13.32000,4.10000,0.00000),V(14.32000,4.10000,0.00000),V(14.32000,3.60000,0.00000),V(13.32000,3.60000,0.00000),V(13.32000,4.10000,0.00000)])]).extrude(V(0,0,0.01200)))
_s.append(Part.Face([_poly([V(5.90000,4.20000,0.00000),V(5.90000,5.68700,0.00000),V(5.79400,5.68700,0.00000),V(5.79400,6.48700,0.00000),V(8.30000,6.48700,0.00000),V(8.30000,6.50000,0.00000),V(9.20000,6.50000,0.00000),V(9.20000,7.80000,0.00000),V(10.80000,7.80000,0.00000),V(10.80000,4.50000,0.00000),V(9.50000,4.50000,0.00000),V(9.50000,5.70000,0.00000),V(8.39400,5.70000,0.00000),V(8.39400,5.68700,0.00000),V(6.90000,5.68700,0.00000),V(6.90000,4.20000,0.00000),V(6.90000,3.70000,0.00000),V(5.90000,3.70000,0.00000),V(5.90000,4.20000,0.00000)])]).extrude(V(0,0,0.01200)))
_s.append(Part.Face([_poly([V(12.20000,4.50000,0.00000),V(12.20000,7.80000,0.00000),V(13.00000,7.80000,0.00000),V(13.00000,10.30000,0.00000),V(14.30000,10.30000,0.00000),V(14.30000,7.80000,0.00000),V(14.30000,4.50000,0.00000),V(14.28300,4.50000,0.00000),V(13.48300,4.50000,0.00000),V(12.20000,4.50000,0.00000)])]).extrude(V(0,0,0.01200)))
_s.append(Part.Face([_poly([V(5.80000,12.70000,0.00000),V(12.30000,12.70000,0.00000),V(12.30000,10.90000,0.00000),V(8.39400,10.90000,0.00000),V(8.39400,10.11300,0.00000),V(5.79400,10.11300,0.00000),V(5.79400,10.91300,0.00000),V(5.80000,10.91300,0.00000),V(5.80000,12.70000,0.00000)])]).extrude(V(0,0,0.01200)))
_s.append(Part.Face([_poly([V(8.50000,16.31300,0.00000),V(5.92000,16.31300,0.00000),V(5.92000,17.11300,0.00000),V(8.52000,17.11300,0.00000),V(8.52000,17.10000,0.00000),V(11.20000,17.10000,0.00000),V(11.20000,15.40000,0.00000),V(9.00000,15.40000,0.00000),V(9.00000,16.30000,0.00000),V(8.50000,16.30000,0.00000),V(8.50000,16.31300,0.00000)])]).extrude(V(0,0,0.01200)))
_s.append(Part.Face([_poly([V(15.86000,4.10000,0.00000),V(16.30000,4.10000,0.00000),V(16.30000,4.50000,0.00000),V(16.09700,4.50000,0.00000),V(16.09700,7.10000,0.00000),V(16.89700,7.10000,0.00000),V(16.89700,5.40000,0.00000),V(16.90000,5.40000,0.00000),V(16.90000,3.60000,0.00000),V(16.86000,3.60000,0.00000),V(16.30000,3.60000,0.00000),V(15.86000,3.60000,0.00000),V(15.86000,4.10000,0.00000)])]).extrude(V(0,0,0.01200)))
_s.append(Part.Face([_poly([V(18.40000,4.10000,0.00000),V(19.40000,4.10000,0.00000),V(19.40000,3.60000,0.00000),V(18.40000,3.60000,0.00000),V(18.40000,4.10000,0.00000)])]).extrude(V(0,0,0.01200)))
_s.append(Part.Face([_poly([V(20.94000,4.10000,0.00000),V(21.94000,4.10000,0.00000),V(21.94000,3.60000,0.00000),V(20.94000,3.60000,0.00000),V(20.94000,4.10000,0.00000)])]).extrude(V(0,0,0.01200)))
_s.append(Part.Face([_poly([V(23.48000,4.10000,0.00000),V(24.48000,4.10000,0.00000),V(24.48000,3.60000,0.00000),V(23.48000,3.60000,0.00000),V(23.48000,4.10000,0.00000)])]).extrude(V(0,0,0.01200)))
_s.append(Part.Face([_poly([V(26.02000,4.10000,0.00000),V(27.02000,4.10000,0.00000),V(27.02000,3.60000,0.00000),V(26.02000,3.60000,0.00000),V(26.02000,4.10000,0.00000)])]).extrude(V(0,0,0.01200)))
_s.append(Part.Face([_poly([V(28.56000,4.10000,0.00000),V(29.56000,4.10000,0.00000),V(29.56000,3.60000,0.00000),V(28.56000,3.60000,0.00000),V(28.56000,4.10000,0.00000)])]).extrude(V(0,0,0.01200)))
_s.append(Part.Face([_poly([V(14.90000,11.70000,0.00000),V(14.90000,13.00000,0.00000),V(16.50000,13.00000,0.00000),V(16.50000,11.40000,0.00000),V(15.15000,11.40000,0.00000),V(15.15000,10.65000,0.00000),V(13.80000,10.65000,0.00000),V(13.80000,10.95000,0.00000),V(14.85000,10.95000,0.00000),V(14.85000,11.70000,0.00000),V(14.90000,11.70000,0.00000)])]).extrude(V(0,0,0.01200)))
_s.append(Part.Face([_poly([V(13.50000,11.75000,0.00000),V(14.50000,11.75000,0.00000),V(14.50000,11.45000,0.00000),V(13.50000,11.45000,0.00000),V(13.50000,11.75000,0.00000)])]).extrude(V(0,0,0.01200)))
_s.append(Part.Face([_poly([V(18.50000,11.45000,0.00000),V(17.40000,11.45000,0.00000),V(17.40000,11.75000,0.00000),V(18.50000,11.75000,0.00000),V(18.50000,11.45000,0.00000)])]).extrude(V(0,0,0.01200)))
_s.append(Part.Face([_poly([V(18.50000,12.05000,0.00000),V(17.40000,12.05000,0.00000),V(17.40000,12.35000,0.00000),V(18.50000,12.35000,0.00000),V(18.50000,12.05000,0.00000)])]).extrude(V(0,0,0.01200)))
_s.append(Part.Face([_poly([V(14.50000,12.95000,0.00000),V(14.50000,12.65000,0.00000),V(13.90000,12.65000,0.00000),V(13.90000,12.95000,0.00000),V(14.50000,12.95000,0.00000)])]).extrude(V(0,0,0.01200)))
_s.append(Part.Face([_poly([V(16.80000,12.65000,0.00000),V(16.80000,12.95000,0.00000),V(18.00000,12.95000,0.00000),V(18.00000,12.65000,0.00000),V(16.80000,12.65000,0.00000)])]).extrude(V(0,0,0.01200)))
_add('1st Routing Conductor' + '_L3', _fuse(_s), (1.0000,0.5020,0.2510))
# --- layer 4 (Routing Dielectric) : z 0.0120..0.0420 mm ---
_s = []
_s.append(Part.Face([_poly([V(17.09700,3.50000,0.01200),V(13.28300,3.50000,0.01200),V(13.28300,8.10000,0.01200),V(17.09700,8.10000,0.01200),V(17.09700,3.50000,0.01200)])]).extrude(V(0,0,0.03000)))
_s.append(Part.Face([_poly([V(4.79400,11.11300,0.01200),V(9.39400,11.11300,0.01200),V(9.39400,5.48700,0.01200),V(4.79400,5.48700,0.01200),V(4.79400,11.11300,0.01200)])]).extrude(V(0,0,0.03000)))
_s.append(Part.Face([_poly([V(4.92000,17.31300,0.01200),V(9.52000,17.31300,0.01200),V(9.52000,11.68700,0.01200),V(4.92000,11.68700,0.01200),V(4.92000,17.31300,0.01200)])]).extrude(V(0,0,0.03000)))
_add('Routing Dielectric' + '_L4', _fuse(_s), (0.9608,0.5098,0.1922))
# --- layer 17 (300K Ohms RES) : z 0.1890..0.2040 mm ---
_s = []
_s.append(Part.Face([_poly([V(16.39700,4.80000,0.18900),V(13.98300,4.80000,0.18900),V(13.98300,6.80000,0.18900),V(16.39700,6.80000,0.18900),V(16.39700,4.80000,0.18900)])]).extrude(V(0,0,0.01500)))
_s.append(Part.Face([_poly([V(6.09400,10.41300,0.18900),V(8.09400,10.41300,0.18900),V(8.09400,6.18700,0.18900),V(6.09400,6.18700,0.18900),V(6.09400,10.41300,0.18900)])]).extrude(V(0,0,0.01500)))
_s.append(Part.Face([_poly([V(6.22000,16.61300,0.18900),V(8.22000,16.61300,0.18900),V(8.22000,12.38700,0.18900),V(6.22000,12.38700,0.18900),V(6.22000,16.61300,0.18900)])]).extrude(V(0,0,0.01500)))
_add('300K Ohms RES' + '_L17', _fuse(_s), (0.2353,0.7059,0.2941))
# --- layer 19 (Resister Glaze) : z 0.2190..0.2390 mm ---
_s = []
_s.append(Part.Face([_poly([V(16.69700,4.50000,0.21900),V(13.68300,4.50000,0.21900),V(13.68300,7.10000,0.21900),V(16.69700,7.10000,0.21900),V(16.69700,4.50000,0.21900)])]).extrude(V(0,0,0.02000)))
_s.append(Part.Face([_poly([V(5.79400,10.71300,0.21900),V(8.39400,10.71300,0.21900),V(8.39400,5.88700,0.21900),V(5.79400,5.88700,0.21900),V(5.79400,10.71300,0.21900)])]).extrude(V(0,0,0.02000)))
_s.append(Part.Face([_poly([V(5.92000,16.91300,0.21900),V(8.52000,16.91300,0.21900),V(8.52000,12.08700,0.21900),V(5.92000,12.08700,0.21900),V(5.92000,16.91300,0.21900)])]).extrude(V(0,0,0.02000)))
_add('Resister Glaze' + '_L19', _fuse(_s), (0.2627,0.3882,0.8471))
# --- layer 55 (L55) : z 0.2540..0.2640 mm ---
_s = []
_s.append(Part.Face([_poly([V(9.20000,6.50000,0.25400),V(9.20000,7.80000,0.25400),V(10.80000,7.80000,0.25400),V(10.80000,4.50000,0.25400),V(9.50000,4.50000,0.25400),V(9.50000,5.70000,0.25400),V(8.39400,5.70000,0.25400),V(8.39400,5.68700,0.25400),V(6.90000,5.68700,0.25400),V(6.90000,4.20000,0.25400),V(5.90000,4.20000,0.25400),V(5.90000,5.68700,0.25400),V(5.79400,5.68700,0.25400),V(5.79400,6.48700,0.25400),V(8.30000,6.48700,0.25400),V(8.30000,6.50000,0.25400),V(9.20000,6.50000,0.25400)])]).extrude(V(0,0,0.01000)))
_s.append(Part.Face([_poly([V(11.55000,8.20000,0.25400),V(11.55000,4.00000,0.25400),V(11.25000,4.00000,0.25400),V(11.25000,8.20000,0.25400),V(10.10000,8.20000,0.25400),V(9.00000,8.20000,0.25400),V(9.00000,9.90000,0.25400),V(12.40000,9.90000,0.25400),V(12.40000,8.20000,0.25400),V(11.55000,8.20000,0.25400)])]).extrude(V(0,0,0.01000)))
_s.append(Part.Face([_poly([V(14.33300,5.20000,0.25400),V(14.20000,5.20000,0.25400),V(14.20000,4.50000,0.25400),V(12.10000,4.50000,0.25400),V(12.10000,7.80000,0.25400),V(13.00000,7.80000,0.25400),V(13.00000,10.30000,0.25400),V(14.30000,10.30000,0.25400),V(14.30000,7.80000,0.25400),V(14.33300,7.80000,0.25400),V(14.33300,5.20000,0.25400)])]).extrude(V(0,0,0.01000)))
_s.append(Part.Face([_poly([V(5.79400,10.11300,0.25400),V(5.79400,10.91300,0.25400),V(5.80000,10.91300,0.25400),V(5.80000,12.70000,0.25400),V(12.30000,12.70000,0.25400),V(12.30000,10.90000,0.25400),V(8.39400,10.90000,0.25400),V(8.39400,10.11300,0.25400),V(5.79400,10.11300,0.25400)])]).extrude(V(0,0,0.01000)))
_s.append(Part.Face([_poly([V(14.50000,11.75000,0.25400),V(14.50000,11.45000,0.25400),V(13.50000,11.45000,0.25400),V(13.50000,11.75000,0.25400),V(14.50000,11.75000,0.25400)])]).extrude(V(0,0,0.01000)))
_s.append(Part.Face([_poly([V(14.50000,12.35000,0.25400),V(14.50000,12.05000,0.25400),V(13.50000,12.05000,0.25400),V(13.50000,12.35000,0.25400),V(14.50000,12.35000,0.25400)])]).extrude(V(0,0,0.01000)))
_s.append(Part.Face([_poly([V(8.52000,16.31300,0.25400),V(5.92000,16.31300,0.25400),V(5.92000,17.11300,0.25400),V(8.52000,17.11300,0.25400),V(8.52000,16.31300,0.25400)])]).extrude(V(0,0,0.01000)))
_s.append(Part.Face([_poly([V(16.90000,5.20000,0.25400),V(16.90000,3.60000,0.25400),V(16.30000,3.60000,0.25400),V(16.30000,5.20000,0.25400),V(16.14700,5.20000,0.25400),V(16.14700,7.80000,0.25400),V(16.94700,7.80000,0.25400),V(16.94700,5.20000,0.25400),V(16.90000,5.20000,0.25400)])]).extrude(V(0,0,0.01000)))
_s.append(Part.Face([_poly([V(17.10000,11.25000,0.25400),V(17.10000,11.55000,0.25400),V(18.10000,11.55000,0.25400),V(18.10000,11.25000,0.25400),V(17.10000,11.25000,0.25400)])]).extrude(V(0,0,0.01000)))
_s.append(Part.Face([_poly([V(15.55000,11.40000,0.25400),V(14.90000,11.40000,0.25400),V(14.90000,13.00000,0.25400),V(16.50000,13.00000,0.25400),V(16.50000,11.40000,0.25400),V(15.85000,11.40000,0.25400),V(15.85000,10.85000,0.25400),V(14.50000,10.85000,0.25400),V(14.40000,10.85000,0.25400),V(13.50000,10.85000,0.25400),V(13.50000,11.15000,0.25400),V(14.40000,11.15000,0.25400),V(14.50000,11.15000,0.25400),V(15.55000,11.15000,0.25400),V(15.55000,11.40000,0.25400)])]).extrude(V(0,0,0.01000)))
_s.append(Part.Face([_poly([V(16.90000,12.05000,0.25400),V(16.90000,12.35000,0.25400),V(18.10000,12.35000,0.25400),V(18.10000,12.05000,0.25400),V(16.90000,12.05000,0.25400)])]).extrude(V(0,0,0.01000)))
_s.append(Part.Face([_poly([V(16.90000,12.65000,0.25400),V(16.90000,12.95000,0.25400),V(18.10000,12.95000,0.25400),V(18.10000,12.65000,0.25400),V(16.90000,12.65000,0.25400)])]).extrude(V(0,0,0.01000)))
_s.append(Part.Face([_poly([V(14.50000,12.95000,0.25400),V(14.50000,12.65000,0.25400),V(13.75000,12.65000,0.25400),V(13.75000,13.40000,0.25400),V(14.05000,13.40000,0.25400),V(14.05000,12.95000,0.25400),V(14.50000,12.95000,0.25400)])]).extrude(V(0,0,0.01000)))
_add('L55' + '_L55', _fuse(_s), (0.9412,0.1961,0.9020))
# --- layer 56 (L56) : z 0.2640..0.2740 mm ---
_s = []
_s.append(Part.Face([_poly([V(11.55000,8.20000,0.26400),V(11.55000,4.00000,0.26400),V(11.25000,4.00000,0.26400),V(11.25000,8.20000,0.26400),V(11.55000,8.20000,0.26400)])]).extrude(V(0,0,0.01000)))
_s.append(Part.Face([_poly([V(15.55000,11.15000,0.26400),V(15.55000,11.40000,0.26400),V(15.85000,11.40000,0.26400),V(15.85000,10.85000,0.26400),V(14.50000,10.85000,0.26400),V(14.40000,10.85000,0.26400),V(13.50000,10.85000,0.26400),V(13.50000,11.15000,0.26400),V(14.40000,11.15000,0.26400),V(14.50000,11.15000,0.26400),V(15.55000,11.15000,0.26400)])]).extrude(V(0,0,0.01000)))
_s.append(Part.Face([_poly([V(18.10000,11.25000,0.26400),V(17.10000,11.25000,0.26400),V(17.10000,11.55000,0.26400),V(18.10000,11.55000,0.26400),V(18.10000,11.25000,0.26400)])]).extrude(V(0,0,0.01000)))
_s.append(Part.Face([_poly([V(13.50000,11.75000,0.26400),V(14.50000,11.75000,0.26400),V(14.50000,11.45000,0.26400),V(13.50000,11.45000,0.26400),V(13.50000,11.75000,0.26400)])]).extrude(V(0,0,0.01000)))
_s.append(Part.Face([_poly([V(13.50000,12.35000,0.26400),V(14.50000,12.35000,0.26400),V(14.50000,12.05000,0.26400),V(13.50000,12.05000,0.26400),V(13.50000,12.35000,0.26400)])]).extrude(V(0,0,0.01000)))
_s.append(Part.Face([_poly([V(18.10000,12.05000,0.26400),V(16.90000,12.05000,0.26400),V(16.90000,12.35000,0.26400),V(18.10000,12.35000,0.26400),V(18.10000,12.05000,0.26400)])]).extrude(V(0,0,0.01000)))
_s.append(Part.Face([_poly([V(18.10000,12.65000,0.26400),V(16.90000,12.65000,0.26400),V(16.90000,12.95000,0.26400),V(18.10000,12.95000,0.26400),V(18.10000,12.65000,0.26400)])]).extrude(V(0,0,0.01000)))
_s.append(Part.Face([_poly([V(14.05000,12.95000,0.26400),V(14.50000,12.95000,0.26400),V(14.50000,12.65000,0.26400),V(13.75000,12.65000,0.26400),V(13.75000,13.40000,0.26400),V(14.05000,13.40000,0.26400),V(14.05000,12.95000,0.26400)])]).extrude(V(0,0,0.01000)))
_add('L56' + '_L56', _fuse(_s), (0.7373,0.9647,0.0471))
# --- layer 58 (Chip_Pads) : z 0.9090..0.9190 mm ---
_s = []
_s.append(Part.Face([_poly([V(15.15000,11.65000,0.90900),V(15.15000,12.75000,0.90900),V(16.25000,12.75000,0.90900),V(16.25000,11.65000,0.90900),V(15.15000,11.65000,0.90900)])]).extrude(V(0,0,0.01000)))
_s.append(Part.Face([_poly([V(21.85000,9.25000,0.90900),V(21.85000,10.35000,0.90900),V(22.95000,10.35000,0.90900),V(22.95000,9.25000,0.90900),V(21.85000,9.25000,0.90900)])]).extrude(V(0,0,0.01000)))
_add('Chip_Pads' + '_L58', _fuse(_s), (0.0000,0.5020,0.5020))
# --- wire bonds (layer 59) ---
_bw = []
_bw.append(_bondwire(V(15.40000,12.30000,0.91900), V(14.75000,12.25000,1.16900), V(14.10000,12.20000,0.91900), 0.01500))
_bw.append(_bondwire(V(15.30000,12.10000,0.91900), V(14.75000,11.85000,1.16900), V(14.20000,11.60000,0.91900), 0.01500))
_bw.append(_bondwire(V(15.30000,11.90000,0.91900), V(14.65000,11.35000,1.16900), V(14.00000,10.80000,0.91900), 0.01500))
_bw.append(_bondwire(V(16.10000,12.50000,0.91900), V(16.80000,12.65000,1.16900), V(17.50000,12.80000,0.91900), 0.01500))
_bw.append(_bondwire(V(16.10000,12.10000,0.91900), V(16.85000,12.15000,1.16900), V(17.60000,12.20000,0.91900), 0.01500))
_bw.append(_bondwire(V(16.10000,11.80000,0.91900), V(16.90000,11.70000,1.16900), V(17.70000,11.60000,0.91900), 0.01500))
_add('wire_bonds', _fuse(_bw), (0.9020,0.7451,1.0000))
# --- component CAP_0805 (extrude 0.4000 mm) ---
_add('CAP_0805', Part.Face(_poly([V(13.30000,8.40000,0.93100),V(15.70000,8.40000,0.93100),V(15.70000,10.05000,0.93100),V(13.30000,10.05000,0.93100),V(13.30000,8.40000,0.93100)])).extrude(V(0,0,0.40000)), (0.15,0.15,0.17))
# --- component CAP_1210 (extrude 0.4000 mm) ---
_add('CAP_1210', Part.Face(_poly([V(12.20000,8.50000,0.93100),V(12.20000,12.10000,0.93100),V(9.30000,12.10000,0.93100),V(9.30000,8.50000,0.93100),V(12.20000,8.50000,0.93100)])).extrude(V(0,0,0.40000)), (0.15,0.15,0.17))
# --- component LM741 (extrude 0.4000 mm) ---
_add('LM741', Part.Face(_poly([V(15.15000,11.65000,0.93100),V(16.25000,11.65000,0.93100),V(16.25000,12.75000,0.93100),V(15.15000,12.75000,0.93100),V(15.15000,11.65000,0.93100)])).extrude(V(0,0,0.40000)), (0.15,0.15,0.17))
# --- component CAP_1210 (extrude 0.4000 mm) ---
_add('CAP_1210', Part.Face(_poly([V(9.70000,4.70000,0.93100),V(13.30000,4.70000,0.93100),V(13.30000,7.60000,0.93100),V(9.70000,7.60000,0.93100),V(9.70000,4.70000,0.93100)])).extrude(V(0,0,0.40000)), (0.15,0.15,0.17))
# --- component LM741 (extrude 0.4000 mm) ---
_add('LM741', Part.Face(_poly([V(21.85000,9.25000,0.93100),V(22.95000,9.25000,0.93100),V(22.95000,10.35000,0.93100),V(21.85000,10.35000,0.93100),V(21.85000,9.25000,0.93100)])).extrude(V(0,0,0.40000)), (0.15,0.15,0.17))
# --- component Header_Pin_Round (extrude 0.4000 mm) ---
_add('Header_Pin_Round', Part.Face(_poly([V(5.29400,1.39400,0.93100),V(6.90600,1.39400,0.93100),V(6.90600,3.00600,0.93100),V(5.29400,3.00600,0.93100),V(5.29400,1.39400,0.93100)])).extrude(V(0,0,0.40000)), (0.15,0.15,0.17))
# --- component Header_Pin_Round (extrude 0.4000 mm) ---
_add('Header_Pin_Round', Part.Face(_poly([V(7.83400,1.39400,0.93100),V(9.44600,1.39400,0.93100),V(9.44600,3.00600,0.93100),V(7.83400,3.00600,0.93100),V(7.83400,1.39400,0.93100)])).extrude(V(0,0,0.40000)), (0.15,0.15,0.17))
# --- component Header_Pin_Round (extrude 0.4000 mm) ---
_add('Header_Pin_Round', Part.Face(_poly([V(10.37400,1.39400,0.93100),V(11.98600,1.39400,0.93100),V(11.98600,3.00600,0.93100),V(10.37400,3.00600,0.93100),V(10.37400,1.39400,0.93100)])).extrude(V(0,0,0.40000)), (0.15,0.15,0.17))
# --- component Header_Pin_Round (extrude 0.4000 mm) ---
_add('Header_Pin_Round', Part.Face(_poly([V(12.91400,1.39400,0.93100),V(14.52600,1.39400,0.93100),V(14.52600,3.00600,0.93100),V(12.91400,3.00600,0.93100),V(12.91400,1.39400,0.93100)])).extrude(V(0,0,0.40000)), (0.15,0.15,0.17))
# --- component Header_Pin_Round (extrude 0.4000 mm) ---
_add('Header_Pin_Round', Part.Face(_poly([V(15.45400,1.39400,0.93100),V(17.06600,1.39400,0.93100),V(17.06600,3.00600,0.93100),V(15.45400,3.00600,0.93100),V(15.45400,1.39400,0.93100)])).extrude(V(0,0,0.40000)), (0.15,0.15,0.17))
# --- component Header_Pin_Round (extrude 0.4000 mm) ---
_add('Header_Pin_Round', Part.Face(_poly([V(17.99400,1.39400,0.93100),V(19.60600,1.39400,0.93100),V(19.60600,3.00600,0.93100),V(17.99400,3.00600,0.93100),V(17.99400,1.39400,0.93100)])).extrude(V(0,0,0.40000)), (0.15,0.15,0.17))
# --- component Header_Pin_Round (extrude 0.4000 mm) ---
_add('Header_Pin_Round', Part.Face(_poly([V(20.53400,1.39400,0.93100),V(22.14600,1.39400,0.93100),V(22.14600,3.00600,0.93100),V(20.53400,3.00600,0.93100),V(20.53400,1.39400,0.93100)])).extrude(V(0,0,0.40000)), (0.15,0.15,0.17))
# --- component Header_Pin_Round (extrude 0.4000 mm) ---
_add('Header_Pin_Round', Part.Face(_poly([V(23.07400,1.39400,0.93100),V(24.68600,1.39400,0.93100),V(24.68600,3.00600,0.93100),V(23.07400,3.00600,0.93100),V(23.07400,1.39400,0.93100)])).extrude(V(0,0,0.40000)), (0.15,0.15,0.17))
# --- component Header_Pin_Round (extrude 0.4000 mm) ---
_add('Header_Pin_Round', Part.Face(_poly([V(25.61400,1.39400,0.93100),V(27.22600,1.39400,0.93100),V(27.22600,3.00600,0.93100),V(25.61400,3.00600,0.93100),V(25.61400,1.39400,0.93100)])).extrude(V(0,0,0.40000)), (0.15,0.15,0.17))
# --- component Header_Pin_Round (extrude 0.4000 mm) ---
_add('Header_Pin_Round', Part.Face(_poly([V(28.15400,1.39400,0.93100),V(29.76600,1.39400,0.93100),V(29.76600,3.00600,0.93100),V(28.15400,3.00600,0.93100),V(28.15400,1.39400,0.93100)])).extrude(V(0,0,0.40000)), (0.15,0.15,0.17))
# --- component Header_Pin_Round (extrude 0.4000 mm) ---
_add('Header_Pin_Round', Part.Face(_poly([V(5.29400,17.39400,0.93100),V(6.90600,17.39400,0.93100),V(6.90600,19.00600,0.93100),V(5.29400,19.00600,0.93100),V(5.29400,17.39400,0.93100)])).extrude(V(0,0,0.40000)), (0.15,0.15,0.17))
# --- component Header_Pin_Round (extrude 0.4000 mm) ---
_add('Header_Pin_Round', Part.Face(_poly([V(7.83400,17.39400,0.93100),V(9.44600,17.39400,0.93100),V(9.44600,19.00600,0.93100),V(7.83400,19.00600,0.93100),V(7.83400,17.39400,0.93100)])).extrude(V(0,0,0.40000)), (0.15,0.15,0.17))
# --- component Header_Pin_Round (extrude 0.4000 mm) ---
_add('Header_Pin_Round', Part.Face(_poly([V(10.37400,17.39400,0.93100),V(11.98600,17.39400,0.93100),V(11.98600,19.00600,0.93100),V(10.37400,19.00600,0.93100),V(10.37400,17.39400,0.93100)])).extrude(V(0,0,0.40000)), (0.15,0.15,0.17))
# --- component Header_Pin_Round (extrude 0.4000 mm) ---
_add('Header_Pin_Round', Part.Face(_poly([V(12.91400,17.39400,0.93100),V(14.52600,17.39400,0.93100),V(14.52600,19.00600,0.93100),V(12.91400,19.00600,0.93100),V(12.91400,17.39400,0.93100)])).extrude(V(0,0,0.40000)), (0.15,0.15,0.17))
# --- component Header_Pin_Round (extrude 0.4000 mm) ---
_add('Header_Pin_Round', Part.Face(_poly([V(15.45400,17.39400,0.93100),V(17.06600,17.39400,0.93100),V(17.06600,19.00600,0.93100),V(15.45400,19.00600,0.93100),V(15.45400,17.39400,0.93100)])).extrude(V(0,0,0.40000)), (0.15,0.15,0.17))
# --- component Header_Pin_Round (extrude 0.4000 mm) ---
_add('Header_Pin_Round', Part.Face(_poly([V(17.99400,17.39400,0.93100),V(19.60600,17.39400,0.93100),V(19.60600,19.00600,0.93100),V(17.99400,19.00600,0.93100),V(17.99400,17.39400,0.93100)])).extrude(V(0,0,0.40000)), (0.15,0.15,0.17))
# --- component Header_Pin_Round (extrude 0.4000 mm) ---
_add('Header_Pin_Round', Part.Face(_poly([V(20.53400,17.39400,0.93100),V(22.14600,17.39400,0.93100),V(22.14600,19.00600,0.93100),V(20.53400,19.00600,0.93100),V(20.53400,17.39400,0.93100)])).extrude(V(0,0,0.40000)), (0.15,0.15,0.17))
# --- component Header_Pin_Round (extrude 0.4000 mm) ---
_add('Header_Pin_Round', Part.Face(_poly([V(23.07400,17.39400,0.93100),V(24.68600,17.39400,0.93100),V(24.68600,19.00600,0.93100),V(23.07400,19.00600,0.93100),V(23.07400,17.39400,0.93100)])).extrude(V(0,0,0.40000)), (0.15,0.15,0.17))
# --- component Header_Pin_Round (extrude 0.4000 mm) ---
_add('Header_Pin_Round', Part.Face(_poly([V(25.61400,17.39400,0.93100),V(27.22600,17.39400,0.93100),V(27.22600,19.00600,0.93100),V(25.61400,19.00600,0.93100),V(25.61400,17.39400,0.93100)])).extrude(V(0,0,0.40000)), (0.15,0.15,0.17))
# --- component Header_Pin_Round (extrude 0.4000 mm) ---
_add('Header_Pin_Round', Part.Face(_poly([V(28.15400,17.39400,0.93100),V(29.76600,17.39400,0.93100),V(29.76600,19.00600,0.93100),V(28.15400,19.00600,0.93100),V(28.15400,17.39400,0.93100)])).extrude(V(0,0,0.40000)), (0.15,0.15,0.17))

_doc.recompute()
if _GUI:
    try:
        FreeCADGui.activeDocument().activeView().viewIsometric()
        FreeCADGui.SendMsgToActiveView("ViewFit")
    except Exception:
        pass
