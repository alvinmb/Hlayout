# FreeCAD 3D view of UNTITLED  (cell TOP)
# Generated by HLayout -- run inside FreeCAD: Macro > Macros... > Execute,
# or  freecadcmd this_file.FCMacro
import FreeCAD as App
import Part
from functools import reduce
try:
    import FreeCADGui
    _GUI = True
except Exception:
    _GUI = False

V = App.Vector
_doc = App.newDocument('UNTITLED_TOP')


def _poly(points):
    return Part.makePolygon(points)


def _fuse(solids):
    solids = [s for s in solids if s is not None and not s.isNull()]
    if not solids:
        return None
    return reduce(lambda a, b: a.fuse(b), solids[1:], solids[0]) if len(solids) > 1 else solids[0]


def _add(name, shape, rgb):
    if shape is None:
        return None
    o = _doc.addObject("Part::Feature", name)
    o.Shape = shape
    if _GUI and o.ViewObject is not None:
        o.ViewObject.ShapeColor = rgb
    return o


def _bondwire(p0, apex, p1, radius):
    """A swept loop p0 -> apex -> p1; falls back to a thin box path."""
    try:
        c = Part.BSplineCurve()
        c.interpolate([p0, apex, p1])
        spine = Part.Wire(c.toShape())
        prof = Part.Wire(Part.makeCircle(radius, p0, apex.sub(p0)))
        return spine.makePipeShell([prof], True, True)
    except Exception:
        legs = []
        for a, b in ((p0, apex), (apex, p1)):
            d = b.sub(a)
            L = d.Length
            if L > 1e-6:
                legs.append(Part.makeCylinder(radius, L, a, d))
        legs.append(Part.makeSphere(radius, apex))
        return _fuse(legs)


# --- layer 3 (1st Routing Conductor) : z 0.0000..0.0120 mm ---
_s = []
_s.append(Part.Face([_poly([V(53.46000,6.99300,0.00000),V(53.46000,7.79300,0.00000),V(56.06000,7.79300,0.00000),V(56.06000,6.99300,0.00000),V(55.30000,6.99300,0.00000),V(55.30000,6.30000,0.00000),V(53.50000,6.30000,0.00000),V(53.50000,6.99300,0.00000),V(53.46000,6.99300,0.00000)])]).extrude(V(0,0,0.01200)))
_s.append(Part.Face([_poly([V(49.30000,7.66776,0.00000),V(46.85000,7.75526,0.00000),V(46.85000,20.20000,0.00000),V(46.85000,20.35000,0.00000),V(46.90000,20.35000,0.00000),V(46.90000,20.50000,0.00000),V(47.60000,20.50000,0.00000),V(47.60000,19.40000,0.00000),V(47.15000,19.40000,0.00000),V(47.15000,8.04474,0.00000),V(49.30000,7.96795,0.00000),V(49.30000,8.70000,0.00000),V(52.60000,8.70000,0.00000),V(52.60000,7.20000,0.00000),V(49.30000,7.20000,0.00000),V(49.30000,7.66776,0.00000)])]).extrude(V(0,0,0.01200)))
_s.append(Part.Face([_poly([V(49.30000,11.50000,0.00000),V(56.20000,11.50000,0.00000),V(56.20000,9.60000,0.00000),V(49.30000,9.60000,0.00000),V(49.30000,11.50000,0.00000)])]).extrude(V(0,0,0.01200)))
_s.append(Part.Face([_poly([V(52.60000,12.50000,0.00000),V(52.60000,14.20000,0.00000),V(52.70000,14.20000,0.00000),V(52.74000,14.20000,0.00000),V(52.74000,14.78700,0.00000),V(55.34000,14.78700,0.00000),V(55.34000,14.20000,0.00000),V(57.10000,14.20000,0.00000),V(57.10000,13.80000,0.00000),V(56.10000,13.80000,0.00000),V(56.10000,12.50000,0.00000),V(52.60000,12.50000,0.00000)])]).extrude(V(0,0,0.01200)))
_s.append(Part.Face([_poly([V(52.30000,14.80000,0.00000),V(52.30000,14.68700,0.00000),V(52.31300,14.68700,0.00000),V(52.31300,13.88700,0.00000),V(49.71300,13.88700,0.00000),V(49.71300,14.00000,0.00000),V(48.60000,14.00000,0.00000),V(48.60000,14.80000,0.00000),V(52.30000,14.80000,0.00000)])]).extrude(V(0,0,0.01200)))
_s.append(Part.Face([_poly([V(55.60000,15.70000,0.00000),V(55.60000,18.60000,0.00000),V(55.34000,18.59559,0.00000),V(55.34000,18.41300,0.00000),V(52.74000,18.41300,0.00000),V(52.74000,18.55153,0.00000),V(52.31300,18.54429,0.00000),V(52.31300,18.31300,0.00000),V(49.71300,18.31300,0.00000),V(49.71300,18.50022,0.00000),V(49.70000,18.50000,0.00000),V(49.70000,19.70000,0.00000),V(57.20000,19.70000,0.00000),V(57.20000,15.70000,0.00000),V(55.60000,15.70000,0.00000)])]).extrude(V(0,0,0.01200)))
_s.append(Part.Face([_poly([V(57.50000,6.30000,0.00000),V(57.50000,6.55000,0.00000),V(57.45000,6.55000,0.00000),V(57.45000,11.05000,0.00000),V(58.65000,11.05000,0.00000),V(58.65000,12.25000,0.00000),V(57.25000,12.25000,0.00000),V(57.25000,13.15000,0.00000),V(56.60000,13.15000,0.00000),V(56.60000,13.45000,0.00000),V(57.55000,13.45000,0.00000),V(57.55000,12.55000,0.00000),V(59.65000,12.55000,0.00000),V(59.65000,13.75000,0.00000),V(60.50000,13.75000,0.00000),V(60.50000,13.45000,0.00000),V(59.95000,13.45000,0.00000),V(59.95000,12.25000,0.00000),V(58.95000,12.25000,0.00000),V(58.95000,10.75000,0.00000),V(57.75000,10.75000,0.00000),V(57.75000,7.00000,0.00000),V(58.70000,7.00000,0.00000),V(58.70000,6.30000,0.00000),V(57.50000,6.30000,0.00000)])]).extrude(V(0,0,0.01200)))
_s.append(Part.Face([_poly([V(56.40000,7.10000,0.00000),V(56.75000,7.10000,0.00000),V(56.75000,11.85000,0.00000),V(58.20000,11.85000,0.00000),V(58.20000,11.55000,0.00000),V(57.05000,11.55000,0.00000),V(57.05000,6.40000,0.00000),V(57.00000,6.40000,0.00000),V(57.00000,6.30000,0.00000),V(56.40000,6.30000,0.00000),V(56.40000,7.10000,0.00000)])]).extrude(V(0,0,0.01200)))
_s.append(Part.Face([_poly([V(66.14000,6.48700,0.00000),V(66.14000,7.28700,0.00000),V(68.74000,7.28700,0.00000),V(68.74000,6.48700,0.00000),V(66.14000,6.48700,0.00000)])]).extrude(V(0,0,0.01200)))
_s.append(Part.Face([_poly([V(62.01300,6.88700,0.00000),V(62.01300,7.68700,0.00000),V(64.61300,7.68700,0.00000),V(64.61300,6.88700,0.00000),V(62.01300,6.88700,0.00000)])]).extrude(V(0,0,0.01200)))
_s.append(Part.Face([_poly([V(66.14000,10.91300,0.00000),V(66.14000,11.71300,0.00000),V(68.74000,11.71300,0.00000),V(68.74000,10.91300,0.00000),V(66.14000,10.91300,0.00000)])]).extrude(V(0,0,0.01200)))
_s.append(Part.Face([_poly([V(62.01300,11.31300,0.00000),V(62.01300,12.11300,0.00000),V(64.61300,12.11300,0.00000),V(64.61300,11.31300,0.00000),V(62.01300,11.31300,0.00000)])]).extrude(V(0,0,0.01200)))
_s.append(Part.Face([_poly([V(57.90000,14.40000,0.00000),V(59.30000,14.40000,0.00000),V(59.30000,12.90000,0.00000),V(57.90000,12.90000,0.00000),V(57.90000,14.40000,0.00000)])]).extrude(V(0,0,0.01200)))
_s.append(Part.Face([_poly([V(59.90000,14.55000,0.00000),V(60.05000,14.55000,0.00000),V(60.05000,19.50000,0.00000),V(60.00000,19.50000,0.00000),V(60.00000,20.40000,0.00000),V(60.80000,20.40000,0.00000),V(60.80000,19.50000,0.00000),V(60.35000,19.50000,0.00000),V(60.35000,14.25000,0.00000),V(59.90000,14.25000,0.00000),V(59.90000,14.55000,0.00000)])]).extrude(V(0,0,0.01200)))
_s.append(Part.Face([_poly([V(58.10000,20.40000,0.00000),V(59.60000,20.40000,0.00000),V(59.60000,15.60000,0.00000),V(58.10000,15.60000,0.00000),V(58.10000,20.40000,0.00000)])]).extrude(V(0,0,0.01200)))
_s.append(Part.Face([_poly([V(73.75300,34.30000,0.00000),V(74.55300,34.30000,0.00000),V(74.55300,31.70000,0.00000),V(73.75300,31.70000,0.00000),V(73.75300,34.30000,0.00000)])]).extrude(V(0,0,0.01200)))
_s.append(Part.Face([_poly([V(76.36700,34.30000,0.00000),V(77.16700,34.30000,0.00000),V(77.16700,31.70000,0.00000),V(76.36700,31.70000,0.00000),V(76.36700,34.30000,0.00000)])]).extrude(V(0,0,0.01200)))
_add('1st Routing Conductor' + '_L3', _fuse(_s), (1.0000,0.5020,0.2510))
# --- layer 4 (Routing Dielectric) : z 0.0120..0.0420 mm ---
_s = []
_s.append(Part.Face([_poly([V(52.46000,10.60700,0.01200),V(57.06000,10.60700,0.01200),V(57.06000,6.79300,0.01200),V(52.46000,6.79300,0.01200),V(52.46000,10.60700,0.01200)])]).extrude(V(0,0,0.03000)))
_s.append(Part.Face([_poly([V(65.14000,6.28700,0.01200),V(65.14000,6.68700,0.01200),V(61.01300,6.68700,0.01200),V(61.01300,12.31300,0.01200),V(65.61300,12.31300,0.01200),V(65.61300,11.91300,0.01200),V(69.74000,11.91300,0.01200),V(69.74000,6.28700,0.01200),V(65.14000,6.28700,0.01200)])]).extrude(V(0,0,0.03000)))
_s.append(Part.Face([_poly([V(48.71300,13.68700,0.01200),V(48.71300,19.31300,0.01200),V(51.74000,19.31300,0.01200),V(51.74000,19.41300,0.01200),V(56.34000,19.41300,0.01200),V(56.34000,13.78700,0.01200),V(53.31300,13.78700,0.01200),V(53.31300,13.68700,0.01200),V(48.71300,13.68700,0.01200)])]).extrude(V(0,0,0.03000)))
_s.append(Part.Face([_poly([V(77.36700,30.70000,0.01200),V(73.55300,30.70000,0.01200),V(73.55300,35.30000,0.01200),V(77.36700,35.30000,0.01200),V(77.36700,30.70000,0.01200)])]).extrude(V(0,0,0.03000)))
_add('Routing Dielectric' + '_L4', _fuse(_s), (0.9608,0.5098,0.1922))
# --- layer 17 (300K Ohms RES) : z 0.1890..0.2040 mm ---
_s = []
_s.append(Part.Face([_poly([V(53.76000,9.90700,0.18900),V(55.76000,9.90700,0.18900),V(55.76000,7.49300,0.18900),V(53.76000,7.49300,0.18900),V(53.76000,9.90700,0.18900)])]).extrude(V(0,0,0.01500)))
_s.append(Part.Face([_poly([V(68.44000,11.21300,0.18900),V(68.44000,6.98700,0.18900),V(66.44000,6.98700,0.18900),V(66.44000,11.21300,0.18900),V(68.44000,11.21300,0.18900)])]).extrude(V(0,0,0.01500)))
_s.append(Part.Face([_poly([V(64.31300,11.61300,0.18900),V(64.31300,7.38700,0.18900),V(62.31300,7.38700,0.18900),V(62.31300,11.61300,0.18900),V(64.31300,11.61300,0.18900)])]).extrude(V(0,0,0.01500)))
_s.append(Part.Face([_poly([V(50.01300,18.61300,0.18900),V(52.01300,18.61300,0.18900),V(52.01300,14.38700,0.18900),V(50.01300,14.38700,0.18900),V(50.01300,18.61300,0.18900)])]).extrude(V(0,0,0.01500)))
_s.append(Part.Face([_poly([V(55.04000,18.71300,0.18900),V(55.04000,14.48700,0.18900),V(53.04000,14.48700,0.18900),V(53.04000,18.71300,0.18900),V(55.04000,18.71300,0.18900)])]).extrude(V(0,0,0.01500)))
_s.append(Part.Face([_poly([V(76.66700,32.00000,0.18900),V(74.25300,32.00000,0.18900),V(74.25300,34.00000,0.18900),V(76.66700,34.00000,0.18900),V(76.66700,32.00000,0.18900)])]).extrude(V(0,0,0.01500)))
_add('300K Ohms RES' + '_L17', _fuse(_s), (0.2353,0.7059,0.2941))
# --- layer 19 (Resister Glaze) : z 0.2190..0.2390 mm ---
_s = []
_s.append(Part.Face([_poly([V(53.46000,10.20700,0.21900),V(56.06000,10.20700,0.21900),V(56.06000,7.19300,0.21900),V(53.46000,7.19300,0.21900),V(53.46000,10.20700,0.21900)])]).extrude(V(0,0,0.02000)))
_s.append(Part.Face([_poly([V(68.74000,11.51300,0.21900),V(68.74000,6.68700,0.21900),V(66.14000,6.68700,0.21900),V(66.14000,11.51300,0.21900),V(68.74000,11.51300,0.21900)])]).extrude(V(0,0,0.02000)))
_s.append(Part.Face([_poly([V(64.61300,11.91300,0.21900),V(64.61300,7.08700,0.21900),V(62.01300,7.08700,0.21900),V(62.01300,11.91300,0.21900),V(64.61300,11.91300,0.21900)])]).extrude(V(0,0,0.02000)))
_s.append(Part.Face([_poly([V(49.71300,18.91300,0.21900),V(52.31300,18.91300,0.21900),V(52.31300,14.08700,0.21900),V(49.71300,14.08700,0.21900),V(49.71300,18.91300,0.21900)])]).extrude(V(0,0,0.02000)))
_s.append(Part.Face([_poly([V(55.34000,19.01300,0.21900),V(55.34000,14.18700,0.21900),V(52.74000,14.18700,0.21900),V(52.74000,19.01300,0.21900),V(55.34000,19.01300,0.21900)])]).extrude(V(0,0,0.02000)))
_s.append(Part.Face([_poly([V(76.96700,31.70000,0.21900),V(73.95300,31.70000,0.21900),V(73.95300,34.30000,0.21900),V(76.96700,34.30000,0.21900),V(76.96700,31.70000,0.21900)])]).extrude(V(0,0,0.02000)))
_add('Resister Glaze' + '_L19', _fuse(_s), (0.2627,0.3882,0.8471))
# --- layer 58 (Chip_Pads) : z 0.2540..0.2640 mm ---
_s = []
_s.append(Part.Face([_poly([V(50.35000,28.85000,0.25400),V(50.35000,29.95000,0.25400),V(51.45000,29.95000,0.25400),V(51.45000,28.85000,0.25400),V(50.35000,28.85000,0.25400)])]).extrude(V(0,0,0.01000)))
_s.append(Part.Face([_poly([V(58.05000,13.05000,0.25400),V(58.05000,14.15000,0.25400),V(59.15000,14.15000,0.25400),V(59.15000,13.05000,0.25400),V(58.05000,13.05000,0.25400)])]).extrude(V(0,0,0.01000)))
_add('Chip_Pads' + '_L58', _fuse(_s), (0.0000,0.5020,0.5020))
# --- wire bonds (layer 59) ---
_bw = []
_bw.append(_bondwire(V(47.20000,20.30000,0.26400), V(47.40000,22.05000,0.51400), V(47.60000,23.80000,0.26400), 0.01500))
_bw.append(_bondwire(V(58.20000,13.70000,0.26400), V(57.55000,13.90000,0.51400), V(56.90000,14.10000,0.26400), 0.01500))
_bw.append(_bondwire(V(59.00000,13.50000,0.26400), V(59.55000,13.55000,0.51400), V(60.10000,13.60000,0.26400), 0.01500))
_bw.append(_bondwire(V(58.30000,13.50000,0.26400), V(57.65000,13.40000,0.51400), V(57.00000,13.30000,0.26400), 0.01500))
_bw.append(_bondwire(V(58.20000,13.20000,0.26400), V(58.10000,12.45000,0.51400), V(58.00000,11.70000,0.26400), 0.01500))
_bw.append(_bondwire(V(59.00000,13.90000,0.26400), V(59.60000,14.15000,0.51400), V(60.20000,14.40000,0.26400), 0.01500))
_bw.append(_bondwire(V(56.70000,6.60000,0.26400), V(57.20000,4.75000,0.51400), V(57.70000,2.90000,0.26400), 0.01500))
_bw.append(_bondwire(V(58.40000,6.80000,0.26400), V(59.50000,4.75000,0.51400), V(60.60000,2.70000,0.26400), 0.01500))
_bw.append(_bondwire(V(54.40000,6.50000,0.26400), V(54.90000,4.65000,0.51400), V(55.40000,2.80000,0.26400), 0.01500))
_bw.append(_bondwire(V(58.90000,19.60000,0.26400), V(58.45000,21.65000,0.51400), V(58.00000,23.70000,0.26400), 0.01500))
_bw.append(_bondwire(V(60.50000,19.90000,0.26400), V(60.50000,21.75000,0.51400), V(60.50000,23.60000,0.26400), 0.01500))
_add('wire_bonds', _fuse(_bw), (0.9020,0.7451,1.0000))
# --- component CAP_1210 (extrude 0.4000 mm) ---
_add('CAP_1210', Part.Face(_poly([V(55.80000,16.10000,0.27600),V(59.40000,16.10000,0.27600),V(59.40000,19.00000,0.27600),V(55.80000,19.00000,0.27600),V(55.80000,16.10000,0.27600)])).extrude(V(0,0,0.40000)), (0.15,0.15,0.17))
# --- component CAP_1210 (extrude 0.4000 mm) ---
_add('CAP_1210', Part.Face(_poly([V(52.40000,7.50000,0.27600),V(52.40000,11.10000,0.27600),V(49.50000,11.10000,0.27600),V(49.50000,7.50000,0.27600),V(52.40000,7.50000,0.27600)])).extrude(V(0,0,0.40000)), (0.15,0.15,0.17))
# --- component CAP_1210 (extrude 0.4000 mm) ---
_add('CAP_1210', Part.Face(_poly([V(55.90000,10.20000,0.27600),V(55.90000,13.80000,0.27600),V(53.00000,13.80000,0.27600),V(53.00000,10.20000,0.27600),V(55.90000,10.20000,0.27600)])).extrude(V(0,0,0.40000)), (0.15,0.15,0.17))
# --- component 20_PIN_pkg (extrude 0.4000 mm) ---
_add('20_PIN_pkg', Part.Face(_poly([V(44.10000,-0.60000,0.27600),V(73.50000,-0.60000,0.27600),V(73.50000,27.40000,0.27600),V(44.10000,27.40000,0.27600),V(44.10000,-0.60000,0.27600)])).extrude(V(0,0,0.40000)), (0.15,0.15,0.17))
# --- component Substrate (extrude 0.4000 mm) ---
_add('Substrate', Part.Face(_poly([V(46.30000,6.00000,0.27600),V(71.80000,6.00000,0.27600),V(71.80000,20.90000,0.27600),V(46.30000,20.90000,0.27600),V(46.30000,6.00000,0.27600)])).extrude(V(0,0,0.40000)), (0.15,0.15,0.17))
# --- component LM741 (extrude 0.4000 mm) ---
_add('LM741', Part.Face(_poly([V(58.05000,13.05000,0.27600),V(59.15000,13.05000,0.27600),V(59.15000,14.15000,0.27600),V(58.05000,14.15000,0.27600),V(58.05000,13.05000,0.27600)])).extrude(V(0,0,0.40000)), (0.15,0.15,0.17))
# --- component CAP_1210 (extrude 0.4000 mm) ---
_add('CAP_1210', Part.Face(_poly([V(42.50000,33.50000,0.27600),V(46.10000,33.50000,0.27600),V(46.10000,36.40000,0.27600),V(42.50000,36.40000,0.27600),V(42.50000,33.50000,0.27600)])).extrude(V(0,0,0.40000)), (0.15,0.15,0.17))
# --- component CAP_1210 (extrude 0.4000 mm) ---
_add('CAP_1210', Part.Face(_poly([V(42.80000,29.80000,0.27600),V(46.40000,29.80000,0.27600),V(46.40000,32.70000,0.27600),V(42.80000,32.70000,0.27600),V(42.80000,29.80000,0.27600)])).extrude(V(0,0,0.40000)), (0.15,0.15,0.17))
# --- component CAP_1210 (extrude 0.4000 mm) ---
_add('CAP_1210', Part.Face(_poly([V(48.80000,33.70000,0.27600),V(52.40000,33.70000,0.27600),V(52.40000,36.60000,0.27600),V(48.80000,36.60000,0.27600),V(48.80000,33.70000,0.27600)])).extrude(V(0,0,0.40000)), (0.15,0.15,0.17))
# --- component LM741 (extrude 0.4000 mm) ---
_add('LM741', Part.Face(_poly([V(50.35000,28.85000,0.27600),V(51.45000,28.85000,0.27600),V(51.45000,29.95000,0.27600),V(50.35000,29.95000,0.27600),V(50.35000,28.85000,0.27600)])).extrude(V(0,0,0.40000)), (0.15,0.15,0.17))

_doc.recompute()
if _GUI:
    try:
        FreeCADGui.activeDocument().activeView().viewIsometric()
        FreeCADGui.SendMsgToActiveView("ViewFit")
    except Exception:
        pass
