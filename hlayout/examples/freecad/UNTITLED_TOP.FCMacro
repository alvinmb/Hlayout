# HLayout - thick-film hybrid circuit layout
# Copyright (C) 2026 Alvin Brown
# SPDX-License-Identifier: GPL-3.0-or-later

# FreeCAD 3D view of UNTITLED  (cell TOP)
# Generated by HLayout -- run inside FreeCAD: Macro > Macros... > Execute,
# or  freecadcmd this_file.FCMacro
import FreeCAD as App
import Part
from functools import reduce
_GUI = bool(getattr(App, "GuiUp", False))
if _GUI:
    import FreeCADGui

V = App.Vector
_doc = App.newDocument('UNTITLED_TOP')


def _poly(points):
    return Part.makePolygon(points)


def _fuse(solids):
    # A compound, not a boolean fuse: every layer's polygons were already
    # merged (shapely unary_union) before being written here, so the
    # solids are disjoint and fusing them is pure cost -- a sequential
    # BRep fuse of ~100 many-vertex traces took minutes and looked like
    # a hang. A compound renders, exports and section-probes the same.
    solids = [s for s in solids if s is not None and not s.isNull()]
    if not solids:
        return None
    return solids[0] if len(solids) == 1 else Part.makeCompound(solids)


#: shapes bonds and parts land on: _SURF = films + substrate (what a
#: component sits on), _PROBE = everything solid so far (what a bond
#: end lands on -- die pads, header pins, traces).
_SURF = []
_PROBE = []


def _parts(shape):
    """A shape's individual solids (or the shape itself) -- what the
    probes below test one by one, so their bounding-box prefilter skips
    almost everything instead of sectioning a whole layer compound."""
    try:
        sol = list(shape.Solids)
    except Exception:
        sol = []
    return sol or [shape]


def _add(name, shape, rgb, surface=False, transparency=0):
    if shape is None:
        return None
    o = _doc.addObject("Part::Feature", name)
    o.Shape = shape
    if _GUI and o.ViewObject is not None:
        o.ViewObject.ShapeColor = rgb
        if transparency:
            o.ViewObject.Transparency = int(transparency)
    _PROBE.extend(_parts(o.Shape))
    if surface:
        _SURF.extend(_parts(o.Shape))
    return o


def _top_z(x, y, shapes=None, default=None):
    """Highest solid surface straight below/at (x, y), or `default`."""
    best = None
    for sh in (_PROBE if shapes is None else shapes):
        bb = sh.BoundBox
        if not (bb.XMin - 1e-6 <= x <= bb.XMax + 1e-6 and bb.YMin - 1e-6 <= y <= bb.YMax + 1e-6):
            continue
        try:
            sec = sh.section(Part.makeLine(V(x, y, bb.ZMax + 1.0), V(x, y, bb.ZMin - 1.0)))
        except Exception:
            continue
        for v in sec.Vertexes:
            if best is None or v.Point.z > best:
                best = v.Point.z
    return default if best is None else best


def _surface_z(x0, y0, x1, y1):
    """Where a part with footprint (x0,y0)-(x1,y1) rests: the highest
    film/substrate top under its centre or inset corners (0 if none)."""
    ix, iy = (x1 - x0) * 0.2, (y1 - y0) * 0.2
    pts = [((x0 + x1) / 2.0, (y0 + y1) / 2.0), (x0 + ix, y0 + iy), (x1 - ix, y0 + iy),
           (x1 - ix, y1 - iy), (x0 + ix, y1 - iy)]
    zs = [_top_z(x, y, _SURF) for x, y in pts]
    zs = [z for z in zs if z is not None]
    return max(zs) if zs else 0.0


_MODEL_SHAPES = {}     # path -> shape read once (probing + headless/mirrored use)
_MODEL_TEMPLATES = {}  # path -> first coloured GUI import, re-used via App::Link


def _progress(msg):
    """Report progress and keep the FreeCAD window painting while the
    macro runs -- otherwise a long GUI run looks frozen ("Not
    Responding") although it is still working."""
    App.Console.PrintMessage("HLayout: %s\n" % msg)
    if _GUI:
        try:
            FreeCADGui.updateGui()
        except Exception:
            pass


def _model_shape(path):
    sh = _MODEL_SHAPES.get(path)
    if sh is None:
        sh = Part.Shape()
        sh.read(path)
        _MODEL_SHAPES[path] = sh
    return sh


def _place_model(path, name, x, y, z, rot_deg, mirrored):
    """Bring a STEP/IGES model in at (x, y, z) rotated rot_deg about Z.

    Each file is read ONCE. In the GUI the first instance is imported
    with ImportGui (so the model's own colours survive) into an
    App::Part named `name`; every further instance of the same file is
    an App::Link to that part -- re-importing the STEP per instance was
    what made a GUI run of a populated board take minutes. Headless (or
    mirrored) instances are plain Part::Features sharing one read."""
    _progress("placing %s" % name)
    P = App.Placement(V(x, y, z), App.Rotation(V(0, 0, 1), rot_deg))
    base = _model_shape(path)
    probe = base.copy()
    probe.Placement = P
    if _GUI and not mirrored:
        try:
            tpl = _MODEL_TEMPLATES.get(path)
            if tpl is not None:
                link = _doc.addObject("App::Link", name)
                link.setLink(tpl)
                link.Placement = P
                _PROBE.extend(_parts(probe))
                return link
            import ImportGui
            before = set(o.Name for o in _doc.Objects)
            ImportGui.insert(path, _doc.Name)
            new = [o for o in _doc.Objects if o.Name not in before]
            if new:
                part = _doc.addObject("App::Part", name)
                for o in [o for o in new if not any(p in new for p in o.InList)]:
                    part.addObject(o)
                part.Placement = P
                _MODEL_TEMPLATES[path] = part
                _PROBE.extend(_parts(probe))
                return part
        except Exception as e:
            App.Console.PrintWarning("HLayout: coloured import of %s failed (%s), "
                                     "reading plain shape\n" % (path, e))
    sh = base.copy()
    if mirrored:
        sh = sh.mirror(V(0, 0, 0), V(1, 0, 0))
    o = _doc.addObject("Part::Feature", name)
    o.Shape = sh
    o.Placement = P
    _PROBE.extend(_parts(o.Shape))
    return o


def _bondwire(p0, apex, p1, radius):
    """A swept loop p0 -> apex -> p1; falls back to a thin box path."""
    try:
        c = Part.BSplineCurve()
        c.interpolate([p0, apex, p1])
        spine = Part.Wire(c.toShape())
        prof = Part.Wire(Part.makeCircle(radius, p0, apex.sub(p0)))
        return spine.makePipeShell([prof], True, True)
    except Exception:
        legs = []
        for a, b in ((p0, apex), (apex, p1)):
            d = b.sub(a)
            L = d.Length
            if L > 1e-6:
                legs.append(Part.makeCylinder(radius, L, a, d))
        legs.append(Part.makeSphere(radius, apex))
        return _fuse(legs)


# --- layer 3 (1st Routing Conductor) : z 0.0000..0.0120 mm ---
_s = []
_s.append(Part.Face([_poly([V(54.66000,7.79300,0.00000),V(54.66000,6.99300,0.00000),V(53.05000,6.99300,0.00000),V(53.05000,6.90000,0.00000),V(53.10000,6.90000,0.00000),V(53.10000,6.50000,0.00000),V(52.70000,6.50000,0.00000),V(52.70000,6.90000,0.00000),V(52.75000,6.90000,0.00000),V(52.75000,6.99300,0.00000),V(52.06000,6.99300,0.00000),V(52.06000,7.79300,0.00000),V(54.66000,7.79300,0.00000)])]).extrude(V(0,0,0.01200)))
_s.append(Part.Face([_poly([V(55.85000,6.90000,0.00000),V(55.85000,11.65000,0.00000),V(56.20000,11.65000,0.00000),V(56.20000,11.70000,0.00000),V(56.60000,11.70000,0.00000),V(56.60000,11.30000,0.00000),V(56.20000,11.30000,0.00000),V(56.20000,11.35000,0.00000),V(56.15000,11.35000,0.00000),V(56.15000,6.90000,0.00000),V(56.20000,6.90000,0.00000),V(56.20000,6.50000,0.00000),V(55.80000,6.50000,0.00000),V(55.80000,6.90000,0.00000),V(55.85000,6.90000,0.00000)])]).extrude(V(0,0,0.01200)))
_s.append(Part.Face([_poly([V(47.49600,7.95000,0.00000),V(47.49600,14.33700,0.00000),V(46.97800,14.33700,0.00000),V(46.97800,20.35000,0.00000),V(49.30000,20.35000,0.00000),V(49.30000,20.40000,0.00000),V(49.70000,20.40000,0.00000),V(49.70000,20.00000,0.00000),V(49.30000,20.00000,0.00000),V(49.30000,20.05000,0.00000),V(47.27800,20.05000,0.00000),V(47.27800,14.63700,0.00000),V(47.64600,14.63700,0.00000),V(47.91300,14.63700,0.00000),V(47.91300,14.88700,0.00000),V(50.51300,14.88700,0.00000),V(50.51300,14.08700,0.00000),V(47.91300,14.08700,0.00000),V(47.91300,14.33700,0.00000),V(47.79600,14.33700,0.00000),V(47.79600,8.25000,0.00000),V(48.40000,8.25000,0.00000),V(48.40000,8.50000,0.00000),V(50.90000,8.50000,0.00000),V(50.90000,7.70000,0.00000),V(48.40000,7.70000,0.00000),V(48.40000,7.95000,0.00000),V(47.49600,7.95000,0.00000)])]).extrude(V(0,0,0.01200)))
_s.append(Part.Face([_poly([V(48.40000,10.10000,0.00000),V(48.40000,10.90000,0.00000),V(49.50000,10.90000,0.00000),V(49.50000,10.95000,0.00000),V(51.60000,10.95000,0.00000),V(51.60000,11.20000,0.00000),V(54.10000,11.20000,0.00000),V(54.10000,10.40700,0.00000),V(54.66000,10.40700,0.00000),V(54.66000,9.60700,0.00000),V(52.06000,9.60700,0.00000),V(52.06000,10.40000,0.00000),V(51.60000,10.40000,0.00000),V(51.60000,10.65000,0.00000),V(50.90000,10.65000,0.00000),V(50.90000,10.10000,0.00000),V(48.40000,10.10000,0.00000)])]).extrude(V(0,0,0.01200)))
_s.append(Part.Face([_poly([V(54.10000,13.60000,0.00000),V(54.10000,13.35000,0.00000),V(55.00000,13.35000,0.00000),V(55.00000,13.50000,0.00000),V(55.40000,13.50000,0.00000),V(55.40000,13.10000,0.00000),V(55.35000,13.10000,0.00000),V(55.35000,13.05000,0.00000),V(54.10000,13.05000,0.00000),V(54.10000,12.80000,0.00000),V(51.60000,12.80000,0.00000),V(51.60000,13.60000,0.00000),V(52.29000,13.60000,0.00000),V(52.29000,14.08700,0.00000),V(51.14000,14.08700,0.00000),V(51.14000,14.88700,0.00000),V(53.74000,14.88700,0.00000),V(53.74000,14.08700,0.00000),V(52.59000,14.08700,0.00000),V(52.59000,13.60000,0.00000),V(54.10000,13.60000,0.00000)])]).extrude(V(0,0,0.01200)))
_s.append(Part.Face([_poly([V(57.50400,6.75000,0.00000),V(57.10000,6.75000,0.00000),V(57.10000,6.70000,0.00000),V(56.70000,6.70000,0.00000),V(56.70000,7.10000,0.00000),V(57.10000,7.10000,0.00000),V(57.10000,7.05000,0.00000),V(57.20400,7.05000,0.00000),V(57.20400,12.12500,0.00000),V(55.75000,12.12500,0.00000),V(55.75000,14.10000,0.00000),V(55.70000,14.10000,0.00000),V(55.70000,14.50000,0.00000),V(56.10000,14.50000,0.00000),V(56.10000,14.10000,0.00000),V(56.05000,14.10000,0.00000),V(56.05000,12.42500,0.00000),V(57.35400,12.42500,0.00000),V(58.95000,12.42500,0.00000),V(58.95000,13.40000,0.00000),V(58.90000,13.40000,0.00000),V(58.90000,13.80000,0.00000),V(59.30000,13.80000,0.00000),V(59.30000,13.40000,0.00000),V(59.25000,13.40000,0.00000),V(59.25000,12.12500,0.00000),V(57.50400,12.12500,0.00000),V(57.50400,6.75000,0.00000)])]).extrude(V(0,0,0.01200)))
_s.append(Part.Face([_poly([V(53.74000,18.51300,0.00000),V(51.14000,18.51300,0.00000),V(51.14000,18.76300,0.00000),V(50.51300,18.76300,0.00000),V(50.51300,18.51300,0.00000),V(47.91300,18.51300,0.00000),V(47.91300,19.31300,0.00000),V(50.51300,19.31300,0.00000),V(50.51300,19.06300,0.00000),V(51.14000,19.06300,0.00000),V(51.14000,19.31300,0.00000),V(53.74000,19.31300,0.00000),V(53.74000,19.06300,0.00000),V(55.15000,19.06300,0.00000),V(55.15000,18.80000,0.00000),V(55.40000,18.80000,0.00000),V(55.40000,16.30000,0.00000),V(54.60000,16.30000,0.00000),V(54.60000,18.76300,0.00000),V(53.74000,18.76300,0.00000),V(53.74000,18.51300,0.00000)])]).extrude(V(0,0,0.01200)))
_s.append(Part.Face([_poly([V(59.60000,6.95000,0.00000),V(59.82300,6.95000,0.00000),V(59.82300,15.70000,0.00000),V(62.65000,15.70000,0.00000),V(62.65000,15.20000,0.00000),V(62.70000,15.20000,0.00000),V(62.70000,14.80000,0.00000),V(62.30000,14.80000,0.00000),V(62.30000,15.20000,0.00000),V(62.35000,15.20000,0.00000),V(62.35000,15.40000,0.00000),V(60.12300,15.40000,0.00000),V(60.12300,6.65000,0.00000),V(59.60000,6.65000,0.00000),V(59.60000,6.60000,0.00000),V(59.20000,6.60000,0.00000),V(59.20000,7.00000,0.00000),V(59.60000,7.00000,0.00000),V(59.60000,6.95000,0.00000)])]).extrude(V(0,0,0.01200)))
_s.append(Part.Face([_poly([V(62.50000,6.95000,0.00000),V(62.90300,6.95000,0.00000),V(62.90300,10.70000,0.00000),V(62.90300,11.70000,0.00000),V(60.44600,11.70000,0.00000),V(60.44600,14.75000,0.00000),V(60.80000,14.75000,0.00000),V(60.80000,14.80000,0.00000),V(61.20000,14.80000,0.00000),V(61.20000,14.40000,0.00000),V(60.80000,14.40000,0.00000),V(60.80000,14.45000,0.00000),V(60.74600,14.45000,0.00000),V(60.74600,12.00000,0.00000),V(62.90300,12.00000,0.00000),V(62.90300,12.14800,0.00000),V(63.20000,12.14800,0.00000),V(63.20000,12.50000,0.00000),V(63.60000,12.50000,0.00000),V(63.60000,12.10000,0.00000),V(63.55000,12.10000,0.00000),V(63.55000,11.84800,0.00000),V(63.35500,11.84800,0.00000),V(63.20300,11.84800,0.00000),V(63.20300,10.70000,0.00000),V(63.20300,6.65000,0.00000),V(62.50000,6.65000,0.00000),V(62.50000,6.60000,0.00000),V(62.10000,6.60000,0.00000),V(62.10000,7.00000,0.00000),V(62.50000,7.00000,0.00000),V(62.50000,6.95000,0.00000)])]).extrude(V(0,0,0.01200)))
_s.append(Part.Face([_poly([V(61.50000,11.25000,0.00000),V(61.50000,10.85000,0.00000),V(61.10000,10.85000,0.00000),V(61.10000,10.90000,0.00000),V(60.85000,10.90000,0.00000),V(60.85000,7.20000,0.00000),V(60.90000,7.20000,0.00000),V(60.90000,6.80000,0.00000),V(60.50000,6.80000,0.00000),V(60.50000,7.20000,0.00000),V(60.55000,7.20000,0.00000),V(60.55000,11.20000,0.00000),V(61.10000,11.20000,0.00000),V(61.10000,11.25000,0.00000),V(61.50000,11.25000,0.00000)])]).extrude(V(0,0,0.01200)))
_s.append(Part.Face([_poly([V(58.60100,15.15000,0.00000),V(58.60100,20.25000,0.00000),V(59.10000,20.25000,0.00000),V(59.10000,20.30000,0.00000),V(59.50000,20.30000,0.00000),V(59.50000,19.90000,0.00000),V(59.10000,19.90000,0.00000),V(59.10000,19.95000,0.00000),V(58.90100,19.95000,0.00000),V(58.90100,15.45000,0.00000),V(59.10000,15.45000,0.00000),V(59.10000,15.50000,0.00000),V(59.50000,15.50000,0.00000),V(59.50000,15.10000,0.00000),V(59.10000,15.10000,0.00000),V(59.10000,15.15000,0.00000),V(58.60100,15.15000,0.00000)])]).extrude(V(0,0,0.01200)))
_s.append(Part.Face([_poly([V(57.25000,18.80000,0.00000),V(57.25000,20.25000,0.00000),V(57.30000,20.25000,0.00000),V(57.30000,20.30000,0.00000),V(57.70000,20.30000,0.00000),V(57.70000,19.90000,0.00000),V(57.55000,19.90000,0.00000),V(57.55000,18.80000,0.00000),V(57.80000,18.80000,0.00000),V(57.80000,16.30000,0.00000),V(57.00000,16.30000,0.00000),V(57.00000,18.80000,0.00000),V(57.25000,18.80000,0.00000)])]).extrude(V(0,0,0.01200)))
_s.append(Part.Face([_poly([V(59.80200,18.80000,0.00000),V(59.80200,19.25200,0.00000),V(59.80200,20.15000,0.00000),V(60.80000,20.15000,0.00000),V(60.80000,20.20000,0.00000),V(61.20000,20.20000,0.00000),V(61.20000,19.80000,0.00000),V(60.80000,19.80000,0.00000),V(60.80000,19.85000,0.00000),V(60.10200,19.85000,0.00000),V(60.10200,19.25200,0.00000),V(60.10200,18.80000,0.00000),V(60.30000,18.80000,0.00000),V(60.30000,16.30000,0.00000),V(59.50000,16.30000,0.00000),V(59.50000,18.80000,0.00000),V(59.80200,18.80000,0.00000)])]).extrude(V(0,0,0.01200)))
_s.append(Part.Face([_poly([V(62.15000,19.46300,0.00000),V(63.75400,19.46300,0.00000),V(63.75400,19.71300,0.00000),V(64.90400,19.71300,0.00000),V(64.90400,20.16300,0.00000),V(66.90700,20.16300,0.00000),V(66.90700,20.41300,0.00000),V(69.50700,20.41300,0.00000),V(69.50700,19.61300,0.00000),V(66.90700,19.61300,0.00000),V(66.90700,19.86300,0.00000),V(65.20400,19.86300,0.00000),V(65.20400,19.71300,0.00000),V(66.35400,19.71300,0.00000),V(66.35400,18.91300,0.00000),V(63.75400,18.91300,0.00000),V(63.75400,19.16300,0.00000),V(62.45000,19.16300,0.00000),V(62.45000,18.80000,0.00000),V(62.70000,18.80000,0.00000),V(62.70000,16.30000,0.00000),V(61.90000,16.30000,0.00000),V(61.90000,18.80000,0.00000),V(62.15000,18.80000,0.00000),V(62.15000,19.46300,0.00000)])]).extrude(V(0,0,0.01200)))
_s.append(Part.Face([_poly([V(63.80700,7.19300,0.00000),V(63.80700,7.99300,0.00000),V(66.40700,7.99300,0.00000),V(66.40700,7.19300,0.00000),V(65.75000,7.19300,0.00000),V(65.75000,7.00000,0.00000),V(65.80000,7.00000,0.00000),V(65.80000,6.60000,0.00000),V(65.40000,6.60000,0.00000),V(65.40000,7.00000,0.00000),V(65.45000,7.00000,0.00000),V(65.45000,7.19300,0.00000),V(63.80700,7.19300,0.00000)])]).extrude(V(0,0,0.01200)))
_s.append(Part.Face([_poly([V(69.90000,8.20000,0.00000),V(69.90000,7.95000,0.00000),V(70.35000,7.95000,0.00000),V(70.35000,15.14400,0.00000),V(68.05700,15.14400,0.00000),V(68.05700,15.18700,0.00000),V(66.90700,15.18700,0.00000),V(66.90700,15.98700,0.00000),V(69.50700,15.98700,0.00000),V(69.50700,15.44400,0.00000),V(70.35000,15.44400,0.00000),V(70.35000,19.90000,0.00000),V(70.30000,19.90000,0.00000),V(70.30000,20.30000,0.00000),V(70.70000,20.30000,0.00000),V(70.70000,19.90000,0.00000),V(70.65000,19.90000,0.00000),V(70.65000,15.29400,0.00000),V(70.65000,7.65000,0.00000),V(69.90000,7.65000,0.00000),V(69.90000,7.40000,0.00000),V(67.40000,7.40000,0.00000),V(67.40000,8.20000,0.00000),V(69.90000,8.20000,0.00000)])]).extrude(V(0,0,0.01200)))
_s.append(Part.Face([_poly([V(66.40700,10.50300,0.00000),V(66.40700,9.80700,0.00000),V(63.80700,9.80700,0.00000),V(63.80700,10.60700,0.00000),V(64.95700,10.60700,0.00000),V(64.95700,10.80300,0.00000),V(65.37500,10.80300,0.00000),V(65.37500,12.90000,0.00000),V(64.70000,12.90000,0.00000),V(64.70000,13.20000,0.00000),V(64.65000,13.20000,0.00000),V(64.65000,13.60000,0.00000),V(64.70000,13.60000,0.00000),V(64.70000,14.48700,0.00000),V(63.75400,14.48700,0.00000),V(63.75400,15.28700,0.00000),V(66.35400,15.28700,0.00000),V(66.35400,14.48700,0.00000),V(65.00000,14.48700,0.00000),V(65.00000,13.60000,0.00000),V(65.05000,13.60000,0.00000),V(65.05000,13.20000,0.00000),V(65.52500,13.20000,0.00000),V(65.80000,13.20000,0.00000),V(65.80000,14.30000,0.00000),V(66.60000,14.30000,0.00000),V(66.60000,11.80000,0.00000),V(65.80000,11.80000,0.00000),V(65.80000,12.90000,0.00000),V(65.67500,12.90000,0.00000),V(65.67500,10.80300,0.00000),V(68.45000,10.80300,0.00000),V(68.45000,11.80000,0.00000),V(68.20000,11.80000,0.00000),V(68.20000,14.30000,0.00000),V(69.00000,14.30000,0.00000),V(69.00000,11.80000,0.00000),V(68.75000,11.80000,0.00000),V(68.75000,10.65300,0.00000),V(68.75000,10.60000,0.00000),V(69.90000,10.60000,0.00000),V(69.90000,9.80000,0.00000),V(67.40000,9.80000,0.00000),V(67.40000,10.50300,0.00000),V(66.40700,10.50300,0.00000)])]).extrude(V(0,0,0.01200)))
_add('1st Routing Conductor' + '_L3', _fuse(_s), (1.0000,0.5020,0.2510), surface=True)
# --- layer 17 (300K Ohms RES) : z 0.0120..0.0270 mm ---
_s = []
_s.append(Part.Face([_poly([V(52.36000,9.90700,0.01200),V(54.36000,9.90700,0.01200),V(54.36000,7.49300,0.01200),V(52.36000,7.49300,0.01200),V(52.36000,9.90700,0.01200)])]).extrude(V(0,0,0.01500)))
_s.append(Part.Face([_poly([V(66.10700,10.10700,0.01200),V(66.10700,7.69300,0.01200),V(64.10700,7.69300,0.01200),V(64.10700,10.10700,0.01200),V(66.10700,10.10700,0.01200)])]).extrude(V(0,0,0.01500)))
_s.append(Part.Face([_poly([V(50.21300,18.81300,0.01200),V(50.21300,14.58700,0.01200),V(48.21300,14.58700,0.01200),V(48.21300,18.81300,0.01200),V(50.21300,18.81300,0.01200)])]).extrude(V(0,0,0.01500)))
_s.append(Part.Face([_poly([V(51.44000,18.81300,0.01200),V(53.44000,18.81300,0.01200),V(53.44000,14.58700,0.01200),V(51.44000,14.58700,0.01200),V(51.44000,18.81300,0.01200)])]).extrude(V(0,0,0.01500)))
_s.append(Part.Face([_poly([V(66.05400,19.21300,0.01200),V(66.05400,14.98700,0.01200),V(64.05400,14.98700,0.01200),V(64.05400,19.21300,0.01200),V(66.05400,19.21300,0.01200)])]).extrude(V(0,0,0.01500)))
_s.append(Part.Face([_poly([V(69.20700,19.91300,0.01200),V(69.20700,15.68700,0.01200),V(67.20700,15.68700,0.01200),V(67.20700,19.91300,0.01200),V(69.20700,19.91300,0.01200)])]).extrude(V(0,0,0.01500)))
_add('300K Ohms RES' + '_L17', _fuse(_s), (0.2353,0.7059,0.2941), surface=True)
# --- layer 19 (Resister Glaze) : z 0.0270..0.0470 mm ---
_s = []
_s.append(Part.Face([_poly([V(52.06000,10.20700,0.02700),V(54.66000,10.20700,0.02700),V(54.66000,7.19300,0.02700),V(52.06000,7.19300,0.02700),V(52.06000,10.20700,0.02700)])]).extrude(V(0,0,0.02000)))
_s.append(Part.Face([_poly([V(66.40700,10.40700,0.02700),V(66.40700,7.39300,0.02700),V(63.80700,7.39300,0.02700),V(63.80700,10.40700,0.02700),V(66.40700,10.40700,0.02700)])]).extrude(V(0,0,0.02000)))
_s.append(Part.Face([_poly([V(50.51300,19.11300,0.02700),V(50.51300,14.28700,0.02700),V(47.91300,14.28700,0.02700),V(47.91300,19.11300,0.02700),V(50.51300,19.11300,0.02700)])]).extrude(V(0,0,0.02000)))
_s.append(Part.Face([_poly([V(51.14000,19.11300,0.02700),V(53.74000,19.11300,0.02700),V(53.74000,14.28700,0.02700),V(51.14000,14.28700,0.02700),V(51.14000,19.11300,0.02700)])]).extrude(V(0,0,0.02000)))
_s.append(Part.Face([_poly([V(66.35400,19.51300,0.02700),V(66.35400,14.68700,0.02700),V(63.75400,14.68700,0.02700),V(63.75400,19.51300,0.02700),V(66.35400,19.51300,0.02700)])]).extrude(V(0,0,0.02000)))
_s.append(Part.Face([_poly([V(69.50700,20.21300,0.02700),V(69.50700,15.38700,0.02700),V(66.90700,15.38700,0.02700),V(66.90700,20.21300,0.02700),V(69.50700,20.21300,0.02700)])]).extrude(V(0,0,0.02000)))
_add('Resister Glaze' + '_L19', _fuse(_s), (0.2000,0.7200,0.3500), surface=True, transparency=55)
# --- substrate (layers [57]) : z -0.6350..0 mm ---
_s = []
_s.append(Part.Face([_poly([V(46.29300,6.17600,-0.63500),V(71.79300,6.17600,-0.63500),V(71.79300,21.07600,-0.63500),V(46.29300,21.07600,-0.63500),V(46.29300,6.17600,-0.63500)])]).extrude(V(0,0,0.63500)))
_add('Substrate', _fuse(_s), (0.97, 0.97, 0.95), surface=True)
# --- component CAP_1210 (model) ---
try:
    _place_model('C:\\dev\\hlayout\\examples\\step_models\\chip_wire\\CAP_1210.step', 'C1_CAP_1210', 54.60000, 16.30000, 0.01200, 0.0000, False)
except Exception as _e:
    App.Console.PrintWarning('HLayout: could not read CAP_1210.step for CAP_1210: %s\n' % _e)
# --- component CAP_1210 (model) ---
try:
    _place_model('C:\\dev\\hlayout\\examples\\step_models\\chip_wire\\CAP_1210.step', 'C2_CAP_1210', 50.90000, 7.70000, 0.01200, 90.0000, False)
except Exception as _e:
    App.Console.PrintWarning('HLayout: could not read CAP_1210.step for CAP_1210: %s\n' % _e)
# --- component CAP_1210 (model) ---
try:
    _place_model('C:\\dev\\hlayout\\examples\\step_models\\chip_wire\\CAP_1210.step', 'C3_CAP_1210', 54.10000, 10.40000, 0.01200, 90.0000, False)
except Exception as _e:
    App.Console.PrintWarning('HLayout: could not read CAP_1210.step for CAP_1210: %s\n' % _e)
# --- component 20_PIN_pkg (model) ---
try:
    _place_model('C:\\dev\\hlayout\\examples\\step_models\\chip_wire\\20_PIN_pkg.step', 'J1_20_PIN_pkg', 47.50000, 2.80000, -0.63500, 0.0000, False)
except Exception as _e:
    App.Console.PrintWarning('HLayout: could not read 20_PIN_pkg.step for 20_PIN_pkg: %s\n' % _e)
# --- component LM741 (model) ---
try:
    _place_model('C:\\dev\\hlayout\\examples\\step_models\\chip_wire\\LM741.step', 'ML1_LM741', 57.40000, 13.60000, 0.00000, 0.0000, False)
except Exception as _e:
    App.Console.PrintWarning('HLayout: could not read LM741.step for LM741: %s\n' % _e)
# --- component CAP_1210 (model) ---
try:
    _place_model('C:\\dev\\hlayout\\examples\\step_models\\chip_wire\\CAP_1210.step', 'C6_CAP_1210', 69.00000, 14.30000, 0.01200, 180.0000, False)
except Exception as _e:
    App.Console.PrintWarning('HLayout: could not read CAP_1210.step for CAP_1210: %s\n' % _e)
# --- component CAP_1210 (model) ---
try:
    _place_model('C:\\dev\\hlayout\\examples\\step_models\\chip_wire\\CAP_1210.step', 'C4_CAP_1210', 59.50000, 16.30000, 0.01200, 0.0000, False)
except Exception as _e:
    App.Console.PrintWarning('HLayout: could not read CAP_1210.step for CAP_1210: %s\n' % _e)
# --- component CAP_1210 (model) ---
try:
    _place_model('C:\\dev\\hlayout\\examples\\step_models\\chip_wire\\CAP_1210.step', 'C5_CAP_1210', 69.90000, 7.40000, 0.01200, 90.0000, False)
except Exception as _e:
    App.Console.PrintWarning('HLayout: could not read CAP_1210.step for CAP_1210: %s\n' % _e)
# --- component LM741 (model) ---
try:
    _place_model('C:\\dev\\hlayout\\examples\\step_models\\chip_wire\\LM741.step', 'ML2_LM741', 62.10000, 13.20000, 0.00000, 180.0000, False)
except Exception as _e:
    App.Console.PrintWarning('HLayout: could not read LM741.step for LM741: %s\n' % _e)
# --- wire bonds (layers [59]) ---
_BONDS = [
    (49.50000, 20.20000, 50.10000, 23.70000, 0.05000),
    (57.80200, 13.55500, 59.10000, 13.60000, 0.05000),
    (57.80200, 13.95100, 59.30000, 15.30000, 0.05000),
    (56.00000, 6.70000, 55.30000, 2.90000, 0.05000),
    (56.90000, 6.90000, 57.80000, 3.00000, 0.05000),
    (52.90000, 6.70000, 52.80000, 3.10000, 0.05000),
    (57.50000, 20.10000, 58.00000, 23.70000, 0.05000),
    (59.30000, 20.10000, 60.30000, 23.90000, 0.05000),
    (62.80000, 23.90000, 61.00000, 20.00000, 0.05000),
    (70.60000, 23.80000, 70.50000, 20.10000, 0.05000),
    (62.43000, 13.54600, 62.50000, 15.00000, 0.05000),
    (59.40000, 6.80000, 60.20000, 3.00000, 0.05000),
    (61.70000, 12.85200, 61.30000, 11.05000, 0.05000),
    (65.60000, 6.80000, 67.90000, 3.00000, 0.05000),
    (62.30000, 6.80000, 65.30000, 3.00000, 0.05000),
    (60.70000, 7.00000, 62.80000, 3.00000, 0.05000),
    (61.70000, 13.25000, 61.00000, 14.60000, 0.05000),
    (55.20000, 13.30000, 57.05000, 13.50000, 0.05000),
    (55.90000, 14.30000, 57.05000, 13.70000, 0.05000),
    (64.85000, 13.40000, 62.45000, 13.30000, 0.05000),
    (63.40000, 12.30000, 62.45000, 13.10000, 0.05000),
    (56.40000, 11.50000, 57.04400, 13.26600, 0.05000),
]
_bw = []
for _x0, _y0, _x1, _y1, _r in _BONDS:
    _z0 = _top_z(_x0, _y0, default=0.0)
    _z1 = _top_z(_x1, _y1, default=0.0)
    _za = max(_z0, _z1) + 0.25000
    _bw.append(_bondwire(V(_x0, _y0, _z0), V((_x0 + _x1) / 2.0, (_y0 + _y1) / 2.0, _za), V(_x1, _y1, _z1), _r))
_add('wire_bonds', _fuse(_bw), (0.8310,0.6860,0.2160))

_doc.recompute()
if _GUI:
    try:
        FreeCADGui.activeDocument().activeView().viewIsometric()
        FreeCADGui.SendMsgToActiveView("ViewFit")
    except Exception:
        pass
