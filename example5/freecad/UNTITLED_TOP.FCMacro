# FreeCAD 3D view of UNTITLED  (cell TOP)
# Generated by HLayout -- run inside FreeCAD: Macro > Macros... > Execute,
# or  freecadcmd this_file.FCMacro
import FreeCAD as App
import Part
from functools import reduce
_GUI = bool(getattr(App, "GuiUp", False))
if _GUI:
    import FreeCADGui

V = App.Vector
_doc = App.newDocument('UNTITLED_TOP')


def _poly(points):
    return Part.makePolygon(points)


def _fuse(solids):
    # A compound, not a boolean fuse: every layer's polygons were already
    # merged (shapely unary_union) before being written here, so the
    # solids are disjoint and fusing them is pure cost -- a sequential
    # BRep fuse of ~100 many-vertex traces took minutes and looked like
    # a hang. A compound renders, exports and section-probes the same.
    solids = [s for s in solids if s is not None and not s.isNull()]
    if not solids:
        return None
    return solids[0] if len(solids) == 1 else Part.makeCompound(solids)


#: shapes bonds and parts land on: _SURF = films + substrate (what a
#: component sits on), _PROBE = everything solid so far (what a bond
#: end lands on -- die pads, header pins, traces).
_SURF = []
_PROBE = []


def _parts(shape):
    """A shape's individual solids (or the shape itself) -- what the
    probes below test one by one, so their bounding-box prefilter skips
    almost everything instead of sectioning a whole layer compound."""
    try:
        sol = list(shape.Solids)
    except Exception:
        sol = []
    return sol or [shape]


def _add(name, shape, rgb, surface=False, transparency=0):
    if shape is None:
        return None
    o = _doc.addObject("Part::Feature", name)
    o.Shape = shape
    if _GUI and o.ViewObject is not None:
        o.ViewObject.ShapeColor = rgb
        if transparency:
            o.ViewObject.Transparency = int(transparency)
    _PROBE.extend(_parts(o.Shape))
    if surface:
        _SURF.extend(_parts(o.Shape))
    return o


def _top_z(x, y, shapes=None, default=None):
    """Highest solid surface straight below/at (x, y), or `default`."""
    best = None
    for sh in (_PROBE if shapes is None else shapes):
        bb = sh.BoundBox
        if not (bb.XMin - 1e-6 <= x <= bb.XMax + 1e-6 and bb.YMin - 1e-6 <= y <= bb.YMax + 1e-6):
            continue
        try:
            sec = sh.section(Part.makeLine(V(x, y, bb.ZMax + 1.0), V(x, y, bb.ZMin - 1.0)))
        except Exception:
            continue
        for v in sec.Vertexes:
            if best is None or v.Point.z > best:
                best = v.Point.z
    return default if best is None else best


def _surface_z(x0, y0, x1, y1):
    """Where a part with footprint (x0,y0)-(x1,y1) rests: the highest
    film/substrate top under its centre or inset corners (0 if none)."""
    ix, iy = (x1 - x0) * 0.2, (y1 - y0) * 0.2
    pts = [((x0 + x1) / 2.0, (y0 + y1) / 2.0), (x0 + ix, y0 + iy), (x1 - ix, y0 + iy),
           (x1 - ix, y1 - iy), (x0 + ix, y1 - iy)]
    zs = [_top_z(x, y, _SURF) for x, y in pts]
    zs = [z for z in zs if z is not None]
    return max(zs) if zs else 0.0


_MODEL_SHAPES = {}     # path -> shape read once (probing + headless/mirrored use)
_MODEL_TEMPLATES = {}  # path -> first coloured GUI import, re-used via App::Link


def _progress(msg):
    """Report progress and keep the FreeCAD window painting while the
    macro runs -- otherwise a long GUI run looks frozen ("Not
    Responding") although it is still working."""
    App.Console.PrintMessage("HLayout: %s\n" % msg)
    if _GUI:
        try:
            FreeCADGui.updateGui()
        except Exception:
            pass


def _model_shape(path):
    sh = _MODEL_SHAPES.get(path)
    if sh is None:
        sh = Part.Shape()
        sh.read(path)
        _MODEL_SHAPES[path] = sh
    return sh


def _place_model(path, name, x, y, z, rot_deg, mirrored):
    """Bring a STEP/IGES model in at (x, y, z) rotated rot_deg about Z.

    Each file is read ONCE. In the GUI the first instance is imported
    with ImportGui (so the model's own colours survive) into an
    App::Part named `name`; every further instance of the same file is
    an App::Link to that part -- re-importing the STEP per instance was
    what made a GUI run of a populated board take minutes. Headless (or
    mirrored) instances are plain Part::Features sharing one read."""
    _progress("placing %s" % name)
    P = App.Placement(V(x, y, z), App.Rotation(V(0, 0, 1), rot_deg))
    base = _model_shape(path)
    probe = base.copy()
    probe.Placement = P
    if _GUI and not mirrored:
        try:
            tpl = _MODEL_TEMPLATES.get(path)
            if tpl is not None:
                link = _doc.addObject("App::Link", name)
                link.setLink(tpl)
                link.Placement = P
                _PROBE.extend(_parts(probe))
                return link
            import ImportGui
            before = set(o.Name for o in _doc.Objects)
            ImportGui.insert(path, _doc.Name)
            new = [o for o in _doc.Objects if o.Name not in before]
            if new:
                part = _doc.addObject("App::Part", name)
                for o in [o for o in new if not any(p in new for p in o.InList)]:
                    part.addObject(o)
                part.Placement = P
                _MODEL_TEMPLATES[path] = part
                _PROBE.extend(_parts(probe))
                return part
        except Exception as e:
            App.Console.PrintWarning("HLayout: coloured import of %s failed (%s), "
                                     "reading plain shape\n" % (path, e))
    sh = base.copy()
    if mirrored:
        sh = sh.mirror(V(0, 0, 0), V(1, 0, 0))
    o = _doc.addObject("Part::Feature", name)
    o.Shape = sh
    o.Placement = P
    _PROBE.extend(_parts(o.Shape))
    return o


def _bondwire(p0, apex, p1, radius):
    """A swept loop p0 -> apex -> p1; falls back to a thin box path."""
    try:
        c = Part.BSplineCurve()
        c.interpolate([p0, apex, p1])
        spine = Part.Wire(c.toShape())
        prof = Part.Wire(Part.makeCircle(radius, p0, apex.sub(p0)))
        return spine.makePipeShell([prof], True, True)
    except Exception:
        legs = []
        for a, b in ((p0, apex), (apex, p1)):
            d = b.sub(a)
            L = d.Length
            if L > 1e-6:
                legs.append(Part.makeCylinder(radius, L, a, d))
        legs.append(Part.makeSphere(radius, apex))
        return _fuse(legs)


# --- layer 3 (1st Routing Conductor) : z 0.0000..0.0120 mm ---
_s = []
_s.append(Part.Face([_poly([V(17.02000,-20.75000,0.00000),V(16.12000,-20.75000,0.00000),V(16.12000,-19.85000,0.00000),V(17.02000,-19.85000,0.00000),V(17.02000,-20.75000,0.00000)])]).extrude(V(0,0,0.01200)))
_s.append(Part.Face([_poly([V(19.26000,-18.50000,0.00000),V(19.21000,-18.50000,0.00000),V(19.21000,-18.10000,0.00000),V(19.61000,-18.10000,0.00000),V(19.61000,-18.50000,0.00000),V(19.56000,-18.50000,0.00000),V(19.56000,-19.85000,0.00000),V(19.56000,-20.30000,0.00000),V(19.56000,-20.75000,0.00000),V(18.66000,-20.75000,0.00000),V(18.66000,-19.85000,0.00000),V(19.26000,-19.85000,0.00000),V(19.26000,-18.50000,0.00000)])]).extrude(V(0,0,0.01200)))
_s.append(Part.Face([_poly([V(27.18000,-20.75000,0.00000),V(26.28000,-20.75000,0.00000),V(26.28000,-19.85000,0.00000),V(27.18000,-19.85000,0.00000),V(27.18000,-20.75000,0.00000)])]).extrude(V(0,0,0.01200)))
_s.append(Part.Face([_poly([V(20.77000,-17.66500,0.00000),V(20.77000,-17.75000,0.00000),V(20.37000,-17.75000,0.00000),V(20.37000,-17.70000,0.00000),V(20.13400,-17.70000,0.00000),V(19.97000,-17.70000,0.00000),V(19.97000,-5.15000,0.00000),V(19.92000,-5.15000,0.00000),V(19.92000,-4.75000,0.00000),V(20.32000,-4.75000,0.00000),V(20.32000,-5.15000,0.00000),V(20.27000,-5.15000,0.00000),V(20.27000,-17.36569,0.00000),V(20.28400,-17.36500,0.00000),V(20.37000,-17.36500,0.00000),V(20.37000,-17.35000,0.00000),V(20.77000,-17.35000,0.00000),V(20.77000,-17.36500,0.00000),V(22.62000,-17.36500,0.00000),V(54.69900,-17.36500,0.00000),V(54.69900,-11.10200,0.00000),V(61.68400,-11.10200,0.00000),V(61.83400,-11.10200,0.00000),V(61.98400,-11.10200,0.00000),V(61.98400,-11.25200,0.00000),V(61.98400,-11.40200,0.00000),V(61.83400,-11.40200,0.00000),V(61.68400,-11.40200,0.00000),V(54.99900,-11.40200,0.00000),V(54.99900,-17.66500,0.00000),V(22.77000,-17.66500,0.00000),V(22.77000,-20.45000,0.00000),V(22.10000,-20.45000,0.00000),V(22.10000,-20.75000,0.00000),V(21.20000,-20.75000,0.00000),V(21.20000,-19.85000,0.00000),V(22.10000,-19.85000,0.00000),V(22.10000,-20.15000,0.00000),V(22.47000,-20.15000,0.00000),V(22.47000,-17.66500,0.00000),V(20.77000,-17.66500,0.00000)])]).extrude(V(0,0,0.01200)))
_s.append(Part.Face([_poly([V(25.62800,-19.05000,0.00000),V(26.02800,-19.05000,0.00000),V(26.02800,-19.45000,0.00000),V(25.97800,-19.45000,0.00000),V(25.97800,-20.45000,0.00000),V(24.64000,-20.45000,0.00000),V(24.64000,-20.75000,0.00000),V(23.74000,-20.75000,0.00000),V(23.74000,-19.85000,0.00000),V(24.64000,-19.85000,0.00000),V(24.64000,-20.15000,0.00000),V(25.67800,-20.15000,0.00000),V(25.67800,-19.45000,0.00000),V(25.62800,-19.45000,0.00000),V(25.62800,-19.05000,0.00000)])]).extrude(V(0,0,0.01200)))
_s.append(Part.Face([_poly([V(27.61100,-19.01600,0.00000),V(28.01100,-19.01600,0.00000),V(28.01100,-19.06600,0.00000),V(29.72000,-19.06600,0.00000),V(29.72000,-19.85000,0.00000),V(29.72000,-20.30000,0.00000),V(29.72000,-20.75000,0.00000),V(28.82000,-20.75000,0.00000),V(28.82000,-19.85000,0.00000),V(29.42000,-19.85000,0.00000),V(29.42000,-19.36600,0.00000),V(28.01100,-19.36600,0.00000),V(28.01100,-19.41600,0.00000),V(27.61100,-19.41600,0.00000),V(27.61100,-19.01600,0.00000)])]).extrude(V(0,0,0.01200)))
_s.append(Part.Face([_poly([V(24.70800,-16.00800,0.00000),V(24.30800,-16.00800,0.00000),V(24.30800,-15.60800,0.00000),V(24.70800,-15.60800,0.00000),V(24.70800,-15.65800,0.00000),V(31.11800,-15.65800,0.00000),V(31.11800,-15.60800,0.00000),V(31.51800,-15.60800,0.00000),V(31.51800,-16.00800,0.00000),V(31.11800,-16.00800,0.00000),V(31.11800,-15.95800,0.00000),V(24.70800,-15.95800,0.00000),V(24.70800,-16.00800,0.00000)])]).extrude(V(0,0,0.01200)))
_s.append(Part.Face([_poly([V(23.52000,-13.60000,0.00000),V(23.52000,-13.55000,0.00000),V(22.37000,-13.55000,0.00000),V(22.37000,-4.40000,0.00000),V(22.32000,-4.40000,0.00000),V(22.32000,-4.00000,0.00000),V(22.72000,-4.00000,0.00000),V(22.72000,-4.40000,0.00000),V(22.67000,-4.40000,0.00000),V(22.67000,-13.25000,0.00000),V(23.52000,-13.25000,0.00000),V(23.52000,-13.20000,0.00000),V(23.92000,-13.20000,0.00000),V(23.92000,-13.60000,0.00000),V(23.52000,-13.60000,0.00000)])]).extrude(V(0,0,0.01200)))
_s.append(Part.Face([_poly([V(26.27000,-6.00000,0.00000),V(26.22000,-6.00000,0.00000),V(26.22000,-5.60000,0.00000),V(26.62000,-5.60000,0.00000),V(26.62000,-6.00000,0.00000),V(26.57000,-6.00000,0.00000),V(26.57000,-8.95000,0.00000),V(24.72000,-8.95000,0.00000),V(24.72000,-9.00000,0.00000),V(24.32000,-9.00000,0.00000),V(24.32000,-8.60000,0.00000),V(24.72000,-8.60000,0.00000),V(24.72000,-8.65000,0.00000),V(26.27000,-8.65000,0.00000),V(26.27000,-6.00000,0.00000)])]).extrude(V(0,0,0.01200)))
_s.append(Part.Face([_poly([V(26.28000,-1.85000,0.00000),V(27.18000,-1.85000,0.00000),V(27.18000,-2.15000,0.00000),V(27.18200,-2.15000,0.00000),V(27.18200,-3.21900,0.00000),V(27.18200,-3.24700,0.00000),V(28.72700,-3.24700,0.00000),V(28.72700,-12.57500,0.00000),V(32.04400,-12.57500,0.00000),V(32.04400,-12.52500,0.00000),V(32.44400,-12.52500,0.00000),V(32.44400,-12.92500,0.00000),V(32.04400,-12.92500,0.00000),V(32.04400,-12.87500,0.00000),V(28.42700,-12.87500,0.00000),V(28.42700,-3.54700,0.00000),V(27.03200,-3.54700,0.00000),V(26.19000,-3.54700,0.00000),V(26.19000,-3.59700,0.00000),V(25.79000,-3.59700,0.00000),V(25.79000,-3.19700,0.00000),V(26.19000,-3.19700,0.00000),V(26.19000,-3.24700,0.00000),V(26.88200,-3.24700,0.00000),V(26.88200,-3.21900,0.00000),V(26.88200,-2.75000,0.00000),V(26.28000,-2.75000,0.00000),V(26.28000,-1.85000,0.00000)])]).extrude(V(0,0,0.01200)))
_s.append(Part.Face([_poly([V(17.02000,-2.75000,0.00000),V(16.12000,-2.75000,0.00000),V(16.12000,-1.85000,0.00000),V(17.02000,-1.85000,0.00000),V(17.02000,-2.75000,0.00000)])]).extrude(V(0,0,0.01200)))
_s.append(Part.Face([_poly([V(29.72000,-2.15000,0.00000),V(29.94100,-2.15000,0.00000),V(29.94100,-3.18400,0.00000),V(29.99100,-3.18400,0.00000),V(29.99100,-3.58400,0.00000),V(29.59100,-3.58400,0.00000),V(29.59100,-3.18400,0.00000),V(29.64100,-3.18400,0.00000),V(29.64100,-2.75000,0.00000),V(28.82000,-2.75000,0.00000),V(28.82000,-1.85000,0.00000),V(29.72000,-1.85000,0.00000),V(29.72000,-2.15000,0.00000)])]).extrude(V(0,0,0.01200)))
_s.append(Part.Face([_poly([V(31.36000,-20.75000,0.00000),V(31.36000,-19.85000,0.00000),V(31.66000,-19.85000,0.00000),V(31.66000,-19.03800,0.00000),V(33.32600,-19.03800,0.00000),V(33.32600,-18.98800,0.00000),V(33.72600,-18.98800,0.00000),V(33.72600,-19.38800,0.00000),V(33.32600,-19.38800,0.00000),V(33.32600,-19.33800,0.00000),V(31.96000,-19.33800,0.00000),V(31.96000,-19.85000,0.00000),V(32.26000,-19.85000,0.00000),V(32.26000,-20.75000,0.00000),V(31.36000,-20.75000,0.00000)])]).extrude(V(0,0,0.01200)))
_s.append(Part.Face([_poly([V(35.89300,-19.07200,0.00000),V(35.89300,-19.02200,0.00000),V(36.29300,-19.02200,0.00000),V(36.29300,-19.42200,0.00000),V(35.89300,-19.42200,0.00000),V(35.89300,-19.37200,0.00000),V(34.50000,-19.37200,0.00000),V(34.50000,-19.85000,0.00000),V(34.80000,-19.85000,0.00000),V(34.80000,-20.75000,0.00000),V(33.90000,-20.75000,0.00000),V(33.90000,-19.85000,0.00000),V(34.20000,-19.85000,0.00000),V(34.20000,-19.07200,0.00000),V(35.89300,-19.07200,0.00000)])]).extrude(V(0,0,0.01200)))
_s.append(Part.Face([_poly([V(37.34000,-20.75000,0.00000),V(36.44000,-20.75000,0.00000),V(36.44000,-19.85000,0.00000),V(36.74000,-19.85000,0.00000),V(36.74000,-19.07200,0.00000),V(37.04500,-19.07200,0.00000),V(37.04500,-19.02200,0.00000),V(37.44500,-19.02200,0.00000),V(37.44500,-19.42200,0.00000),V(37.04500,-19.42200,0.00000),V(37.04500,-19.37200,0.00000),V(37.04000,-19.37200,0.00000),V(37.04000,-19.85000,0.00000),V(37.34000,-19.85000,0.00000),V(37.34000,-20.75000,0.00000)])]).extrude(V(0,0,0.01200)))
_s.append(Part.Face([_poly([V(39.88000,-20.75000,0.00000),V(38.98000,-20.75000,0.00000),V(38.98000,-19.85000,0.00000),V(39.28000,-19.85000,0.00000),V(39.28000,-19.39000,0.00000),V(39.23000,-19.39000,0.00000),V(39.23000,-18.99000,0.00000),V(39.63000,-18.99000,0.00000),V(39.63000,-19.39000,0.00000),V(39.58000,-19.39000,0.00000),V(39.58000,-19.85000,0.00000),V(39.88000,-19.85000,0.00000),V(39.88000,-20.75000,0.00000)])]).extrude(V(0,0,0.01200)))
_s.append(Part.Face([_poly([V(39.05500,-10.45600,0.00000),V(39.05500,-14.40200,0.00000),V(47.35000,-14.40200,0.00000),V(47.35000,-15.83100,0.00000),V(49.84500,-15.83100,0.00000),V(49.84500,-15.78100,0.00000),V(50.24500,-15.78100,0.00000),V(50.24500,-16.18100,0.00000),V(49.84500,-16.18100,0.00000),V(49.84500,-16.13100,0.00000),V(47.05000,-16.13100,0.00000),V(47.05000,-14.70200,0.00000),V(38.75500,-14.70200,0.00000),V(38.75500,-10.45600,0.00000),V(38.70500,-10.45600,0.00000),V(38.70500,-10.05600,0.00000),V(39.10500,-10.05600,0.00000),V(39.10500,-10.45600,0.00000),V(39.05500,-10.45600,0.00000)])]).extrude(V(0,0,0.01200)))
_s.append(Part.Face([_poly([V(32.32000,-7.65000,0.00000),V(39.77000,-7.65000,0.00000),V(39.77000,-11.45000,0.00000),V(46.37000,-11.45000,0.00000),V(46.37000,-9.95000,0.00000),V(54.17000,-9.95000,0.00000),V(54.17000,-10.00000,0.00000),V(54.22000,-10.00000,0.00000),V(54.22000,-10.40000,0.00000),V(53.82000,-10.40000,0.00000),V(53.82000,-10.25000,0.00000),V(46.67000,-10.25000,0.00000),V(46.67000,-11.75000,0.00000),V(39.47000,-11.75000,0.00000),V(39.47000,-7.95000,0.00000),V(31.97000,-7.95000,0.00000),V(31.97000,-7.67500,0.00000),V(31.92000,-7.67500,0.00000),V(31.92000,-7.27500,0.00000),V(32.32000,-7.27500,0.00000),V(32.32000,-7.65000,0.00000)])]).extrude(V(0,0,0.01200)))
_s.append(Part.Face([_poly([V(34.06200,-2.75000,0.00000),V(33.90000,-2.75000,0.00000),V(33.90000,-1.85000,0.00000),V(34.80000,-1.85000,0.00000),V(34.80000,-2.75000,0.00000),V(34.58886,-2.75000,0.00000),V(34.58671,-2.75129,0.00000),V(34.57340,-2.75758,0.00000),V(34.55954,-2.76254,0.00000),V(34.54526,-2.76612,0.00000),V(34.53070,-2.76828,0.00000),V(34.51600,-2.76900,0.00000),V(34.36200,-2.76900,0.00000),V(34.36200,-6.91600,0.00000),V(35.34500,-6.91600,0.00000),V(35.34500,-6.86600,0.00000),V(35.74500,-6.86600,0.00000),V(35.74500,-6.91600,0.00000),V(43.02900,-6.91600,0.00000),V(43.02900,-7.13600,0.00000),V(47.21700,-7.13600,0.00000),V(47.21700,-7.07900,0.00000),V(47.21772,-7.06430,0.00000),V(47.21988,-7.04974,0.00000),V(47.22346,-7.03546,0.00000),V(47.22842,-7.02160,0.00000),V(47.23471,-7.00829,0.00000),V(47.24228,-6.99566,0.00000),V(47.25105,-6.98384,0.00000),V(47.26093,-6.97293,0.00000),V(47.27184,-6.96305,0.00000),V(47.28366,-6.95428,0.00000),V(47.29629,-6.94671,0.00000),V(47.30960,-6.94042,0.00000),V(47.32346,-6.93546,0.00000),V(47.33774,-6.93188,0.00000),V(47.35230,-6.92972,0.00000),V(47.36700,-6.92900,0.00000),V(49.92500,-6.92900,0.00000),V(49.93970,-6.92972,0.00000),V(49.95426,-6.93188,0.00000),V(49.96854,-6.93546,0.00000),V(49.98240,-6.94042,0.00000),V(49.99571,-6.94671,0.00000),V(50.00834,-6.95428,0.00000),V(50.02016,-6.96305,0.00000),V(50.03107,-6.97293,0.00000),V(50.04095,-6.98384,0.00000),V(50.04972,-6.99566,0.00000),V(50.05729,-7.00829,0.00000),V(50.06358,-7.02160,0.00000),V(50.06854,-7.03546,0.00000),V(50.07212,-7.04974,0.00000),V(50.07428,-7.06430,0.00000),V(50.07500,-7.07900,0.00000),V(50.07500,-7.50300,0.00000),V(52.33200,-7.50300,0.00000),V(52.33200,-7.81000,0.00000),V(52.33200,-8.46400,0.00000),V(54.93100,-8.46400,0.00000),V(54.94570,-8.46472,0.00000),V(54.96026,-8.46688,0.00000),V(54.97454,-8.47046,0.00000),V(54.98840,-8.47542,0.00000),V(55.00171,-8.48171,0.00000),V(55.01434,-8.48928,0.00000),V(55.02616,-8.49805,0.00000),V(55.03707,-8.50793,0.00000),V(55.04695,-8.51884,0.00000),V(55.05572,-8.53066,0.00000),V(55.06329,-8.54329,0.00000),V(55.06958,-8.55660,0.00000),V(55.07454,-8.57046,0.00000),V(55.07812,-8.58474,0.00000),V(55.08028,-8.59930,0.00000),V(55.08100,-8.61400,0.00000),V(55.08100,-10.09300,0.00000),V(59.82000,-10.09300,0.00000),V(59.82000,-10.04300,0.00000),V(60.22000,-10.04300,0.00000),V(60.22000,-10.44300,0.00000),V(59.82000,-10.44300,0.00000),V(59.82000,-10.39300,0.00000),V(54.78100,-10.39300,0.00000),V(54.78100,-8.76400,0.00000),V(52.03200,-8.76400,0.00000),V(52.03200,-7.81000,0.00000),V(52.03200,-7.80300,0.00000),V(49.77500,-7.80300,0.00000),V(49.77500,-7.22900,0.00000),V(47.51700,-7.22900,0.00000),V(47.51700,-7.43600,0.00000),V(42.72900,-7.43600,0.00000),V(42.72900,-7.21600,0.00000),V(35.74500,-7.21600,0.00000),V(35.74500,-7.26600,0.00000),V(35.34500,-7.26600,0.00000),V(35.34500,-7.21600,0.00000),V(34.06200,-7.21600,0.00000),V(34.06200,-2.75000,0.00000)])]).extrude(V(0,0,0.01200)))
_s.append(Part.Face([_poly([V(35.79700,-4.90900,0.00000),V(63.04200,-4.90900,0.00000),V(63.04200,-3.58100,0.00000),V(62.99200,-3.58100,0.00000),V(62.99200,-3.18100,0.00000),V(63.04200,-3.18100,0.00000),V(63.04200,-2.15000,0.00000),V(64.38000,-2.15000,0.00000),V(64.38000,-1.85000,0.00000),V(65.28000,-1.85000,0.00000),V(65.28000,-2.75000,0.00000),V(64.38000,-2.75000,0.00000),V(64.38000,-2.45000,0.00000),V(63.34200,-2.45000,0.00000),V(63.34200,-3.18100,0.00000),V(63.39200,-3.18100,0.00000),V(63.39200,-3.58100,0.00000),V(63.34200,-3.58100,0.00000),V(63.34200,-5.20900,0.00000),V(35.79700,-5.20900,0.00000),V(35.79700,-5.25900,0.00000),V(35.39700,-5.25900,0.00000),V(35.39700,-4.85900,0.00000),V(35.79700,-4.85900,0.00000),V(35.79700,-4.90900,0.00000)])]).extrude(V(0,0,0.01200)))
_s.append(Part.Face([_poly([V(39.58000,-3.55900,0.00000),V(39.54800,-3.55900,0.00000),V(39.54800,-3.60900,0.00000),V(39.14800,-3.60900,0.00000),V(39.14800,-3.20900,0.00000),V(39.28000,-3.20900,0.00000),V(39.28000,-2.75000,0.00000),V(38.98000,-2.75000,0.00000),V(38.98000,-1.85000,0.00000),V(39.88000,-1.85000,0.00000),V(39.88000,-2.75000,0.00000),V(39.58000,-2.75000,0.00000),V(39.58000,-3.55900,0.00000)])]).extrude(V(0,0,0.01200)))
_s.append(Part.Face([_poly([V(36.59500,-3.57800,0.00000),V(36.19500,-3.57800,0.00000),V(36.19500,-3.52800,0.00000),V(34.97900,-3.52800,0.00000),V(34.97900,-5.95000,0.00000),V(43.72200,-5.95000,0.00000),V(43.72200,-6.51900,0.00000),V(45.69200,-6.51900,0.00000),V(45.69200,-6.29700,0.00000),V(51.10800,-6.29700,0.00000),V(51.10800,-6.62700,0.00000),V(53.63400,-6.62700,0.00000),V(53.63400,-7.21500,0.00000),V(56.88600,-7.21500,0.00000),V(56.88600,-8.93400,0.00000),V(58.79500,-8.93400,0.00000),V(58.79500,-8.88400,0.00000),V(59.19500,-8.88400,0.00000),V(59.19500,-9.28400,0.00000),V(58.79500,-9.28400,0.00000),V(58.79500,-9.23400,0.00000),V(56.58600,-9.23400,0.00000),V(56.58600,-7.51500,0.00000),V(53.33400,-7.51500,0.00000),V(53.33400,-6.92700,0.00000),V(50.80800,-6.92700,0.00000),V(50.80800,-6.59700,0.00000),V(45.99200,-6.59700,0.00000),V(45.99200,-6.81900,0.00000),V(43.42200,-6.81900,0.00000),V(43.42200,-6.25000,0.00000),V(34.67900,-6.25000,0.00000),V(34.67900,-3.22800,0.00000),V(36.19500,-3.22800,0.00000),V(36.19500,-3.17800,0.00000),V(36.59500,-3.17800,0.00000),V(36.59500,-3.22800,0.00000),V(36.74000,-3.22800,0.00000),V(36.74000,-2.75000,0.00000),V(36.44000,-2.75000,0.00000),V(36.44000,-1.85000,0.00000),V(37.34000,-1.85000,0.00000),V(37.34000,-2.75000,0.00000),V(37.04000,-2.75000,0.00000),V(37.04000,-3.52800,0.00000),V(36.59500,-3.52800,0.00000),V(36.59500,-3.57800,0.00000)])]).extrude(V(0,0,0.01200)))
_s.append(Part.Face([_poly([V(31.36000,-2.75000,0.00000),V(31.36000,-1.85000,0.00000),V(32.26000,-1.85000,0.00000),V(32.26000,-2.75000,0.00000),V(31.36000,-2.75000,0.00000)])]).extrude(V(0,0,0.01200)))
_s.append(Part.Face([_poly([V(45.17900,-19.85000,0.00000),V(45.17900,-18.92800,0.00000),V(45.92200,-18.92800,0.00000),V(45.92200,-18.87800,0.00000),V(46.32200,-18.87800,0.00000),V(46.32200,-19.27800,0.00000),V(45.92200,-19.27800,0.00000),V(45.92200,-19.22800,0.00000),V(45.47900,-19.22800,0.00000),V(45.47900,-20.00000,0.00000),V(45.47828,-20.01470,0.00000),V(45.47612,-20.02926,0.00000),V(45.47254,-20.04354,0.00000),V(45.46758,-20.05740,0.00000),V(45.46129,-20.07071,0.00000),V(45.45372,-20.08334,0.00000),V(45.44495,-20.09516,0.00000),V(45.43507,-20.10607,0.00000),V(45.42416,-20.11595,0.00000),V(45.41234,-20.12472,0.00000),V(45.39971,-20.13229,0.00000),V(45.38640,-20.13858,0.00000),V(45.37254,-20.14354,0.00000),V(45.35826,-20.14712,0.00000),V(45.34370,-20.14928,0.00000),V(45.32900,-20.15000,0.00000),V(44.96000,-20.15000,0.00000),V(44.96000,-20.75000,0.00000),V(44.06000,-20.75000,0.00000),V(44.06000,-19.85000,0.00000),V(44.51000,-19.85000,0.00000),V(44.96000,-19.85000,0.00000),V(45.17900,-19.85000,0.00000)])]).extrude(V(0,0,0.01200)))
_s.append(Part.Face([_poly([V(41.80300,-19.40700,0.00000),V(41.80300,-19.00700,0.00000),V(42.20300,-19.00700,0.00000),V(42.20300,-19.40700,0.00000),V(42.12000,-19.40700,0.00000),V(42.12000,-19.85000,0.00000),V(42.42000,-19.85000,0.00000),V(42.42000,-20.75000,0.00000),V(41.52000,-20.75000,0.00000),V(41.52000,-19.85000,0.00000),V(41.82000,-19.85000,0.00000),V(41.82000,-19.40700,0.00000),V(41.80300,-19.40700,0.00000)])]).extrude(V(0,0,0.01200)))
_s.append(Part.Face([_poly([V(46.90000,-19.05600,0.00000),V(47.29500,-19.05600,0.00000),V(47.29500,-19.00600,0.00000),V(47.34500,-19.00600,0.00000),V(47.34500,-17.98200,0.00000),V(56.97000,-17.98200,0.00000),V(56.97000,-17.93200,0.00000),V(57.37000,-17.93200,0.00000),V(57.37000,-18.33200,0.00000),V(56.97000,-18.33200,0.00000),V(56.97000,-18.28200,0.00000),V(47.64500,-18.28200,0.00000),V(47.64500,-19.00600,0.00000),V(47.69500,-19.00600,0.00000),V(47.69500,-19.40600,0.00000),V(47.29500,-19.40600,0.00000),V(47.29500,-19.35600,0.00000),V(47.20000,-19.35600,0.00000),V(47.20000,-19.85000,0.00000),V(47.50000,-19.85000,0.00000),V(47.50000,-20.75000,0.00000),V(46.60000,-20.75000,0.00000),V(46.60000,-19.85000,0.00000),V(46.90000,-19.85000,0.00000),V(46.90000,-19.05600,0.00000)])]).extrude(V(0,0,0.01200)))
_s.append(Part.Face([_poly([V(39.23000,-16.36600,0.00000),V(39.23000,-15.96600,0.00000),V(39.63000,-15.96600,0.00000),V(39.63000,-16.36600,0.00000),V(39.58000,-16.36600,0.00000),V(39.58000,-16.59800,0.00000),V(46.69300,-16.59800,0.00000),V(46.69300,-16.54800,0.00000),V(47.09300,-16.54800,0.00000),V(47.09300,-16.94800,0.00000),V(46.69300,-16.94800,0.00000),V(46.69300,-16.89800,0.00000),V(39.28000,-16.89800,0.00000),V(39.28000,-16.36600,0.00000),V(39.23000,-16.36600,0.00000)])]).extrude(V(0,0,0.01200)))
_s.append(Part.Face([_poly([V(45.66800,-9.06600,0.00000),V(53.57600,-9.06600,0.00000),V(53.57600,-9.17000,0.00000),V(53.62600,-9.17000,0.00000),V(53.62600,-9.57000,0.00000),V(53.22600,-9.57000,0.00000),V(53.22600,-9.36600,0.00000),V(45.96800,-9.36600,0.00000),V(45.96800,-10.66700,0.00000),V(46.01800,-10.66700,0.00000),V(46.01800,-11.06700,0.00000),V(45.61800,-11.06700,0.00000),V(45.61800,-10.66700,0.00000),V(45.66800,-10.66700,0.00000),V(45.66800,-9.06600,0.00000)])]).extrude(V(0,0,0.01200)))
_s.append(Part.Face([_poly([V(50.53000,-8.22100,0.00000),V(50.93000,-8.22100,0.00000),V(50.93000,-8.62100,0.00000),V(50.88000,-8.62100,0.00000),V(50.88000,-8.74900,0.00000),V(43.49900,-8.74900,0.00000),V(43.49900,-8.89100,0.00000),V(43.09900,-8.89100,0.00000),V(43.09900,-8.49100,0.00000),V(43.14900,-8.49100,0.00000),V(43.14900,-8.44900,0.00000),V(50.53000,-8.44900,0.00000),V(50.53000,-8.22100,0.00000)])]).extrude(V(0,0,0.01200)))
_s.append(Part.Face([_poly([V(48.84200,-7.76800,0.00000),V(48.84200,-7.63100,0.00000),V(49.24200,-7.63100,0.00000),V(49.24200,-8.03100,0.00000),V(49.19200,-8.03100,0.00000),V(49.19200,-8.06800,0.00000),V(42.23500,-8.06800,0.00000),V(42.23500,-8.11800,0.00000),V(41.83500,-8.11800,0.00000),V(41.83500,-7.71800,0.00000),V(42.23500,-7.71800,0.00000),V(42.23500,-7.76800,0.00000),V(48.84200,-7.76800,0.00000)])]).extrude(V(0,0,0.01200)))
_s.append(Part.Face([_poly([V(51.87600,-5.68000,0.00000),V(51.87600,-5.80900,0.00000),V(51.92600,-5.80900,0.00000),V(51.92600,-5.96100,0.00000),V(56.31900,-5.96100,0.00000),V(56.31900,-5.91100,0.00000),V(56.71900,-5.91100,0.00000),V(56.71900,-6.31100,0.00000),V(56.31900,-6.31100,0.00000),V(56.31900,-6.26100,0.00000),V(51.57600,-6.26100,0.00000),V(51.57600,-6.20900,0.00000),V(51.52600,-6.20900,0.00000),V(51.52600,-5.98000,0.00000),V(44.54000,-5.98000,0.00000),V(44.54000,-6.03000,0.00000),V(44.14000,-6.03000,0.00000),V(44.14000,-5.63000,0.00000),V(44.54000,-5.63000,0.00000),V(44.54000,-5.68000,0.00000),V(51.87600,-5.68000,0.00000)])]).extrude(V(0,0,0.01200)))
_s.append(Part.Face([_poly([V(47.49900,-3.98600,0.00000),V(47.49900,-3.55200,0.00000),V(46.90000,-3.55200,0.00000),V(46.90000,-2.75000,0.00000),V(46.60000,-2.75000,0.00000),V(46.60000,-1.85000,0.00000),V(47.50000,-1.85000,0.00000),V(47.50000,-2.75000,0.00000),V(47.20000,-2.75000,0.00000),V(47.20000,-3.25200,0.00000),V(47.64900,-3.25200,0.00000),V(48.04700,-3.25200,0.00000),V(48.04700,-3.20200,0.00000),V(48.44700,-3.20200,0.00000),V(48.44700,-3.60200,0.00000),V(48.04700,-3.60200,0.00000),V(48.04700,-3.55200,0.00000),V(47.79900,-3.55200,0.00000),V(47.79900,-4.28600,0.00000),V(40.57800,-4.28600,0.00000),V(40.57800,-4.33600,0.00000),V(40.17800,-4.33600,0.00000),V(40.17800,-3.93600,0.00000),V(40.57800,-3.93600,0.00000),V(40.57800,-3.98600,0.00000),V(47.49900,-3.98600,0.00000)])]).extrude(V(0,0,0.01200)))
_s.append(Part.Face([_poly([V(44.36000,-2.75000,0.00000),V(44.06000,-2.75000,0.00000),V(44.06000,-1.85000,0.00000),V(44.96000,-1.85000,0.00000),V(44.96000,-2.75000,0.00000),V(44.66000,-2.75000,0.00000),V(44.66000,-3.21800,0.00000),V(46.05900,-3.21800,0.00000),V(46.05900,-3.16800,0.00000),V(46.45900,-3.16800,0.00000),V(46.45900,-3.56800,0.00000),V(46.05900,-3.56800,0.00000),V(46.05900,-3.51800,0.00000),V(44.36000,-3.51800,0.00000),V(44.36000,-2.75000,0.00000)])]).extrude(V(0,0,0.01200)))
_s.append(Part.Face([_poly([V(42.42000,-2.75000,0.00000),V(41.52000,-2.75000,0.00000),V(41.52000,-1.85000,0.00000),V(42.42000,-1.85000,0.00000),V(42.42000,-2.75000,0.00000)])]).extrude(V(0,0,0.01200)))
_s.append(Part.Face([_poly([V(51.68000,-20.75000,0.00000),V(51.68000,-20.45000,0.00000),V(51.59500,-20.45000,0.00000),V(51.59500,-19.90000,0.00000),V(51.54500,-19.90000,0.00000),V(51.54500,-19.50000,0.00000),V(51.94500,-19.50000,0.00000),V(51.94500,-19.85000,0.00000),V(52.58000,-19.85000,0.00000),V(52.58000,-20.75000,0.00000),V(51.68000,-20.75000,0.00000)])]).extrude(V(0,0,0.01200)))
_s.append(Part.Face([_poly([V(49.12000,-19.82500,0.00000),V(49.12000,-19.42500,0.00000),V(49.52000,-19.42500,0.00000),V(49.52000,-19.82500,0.00000),V(49.47000,-19.82500,0.00000),V(49.47000,-19.85000,0.00000),V(49.59000,-19.85000,0.00000),V(50.04000,-19.85000,0.00000),V(50.04000,-20.75000,0.00000),V(49.14000,-20.75000,0.00000),V(49.14000,-19.85000,0.00000),V(49.17000,-19.85000,0.00000),V(49.17000,-19.82500,0.00000),V(49.12000,-19.82500,0.00000)])]).extrude(V(0,0,0.01200)))
_s.append(Part.Face([_poly([V(54.22000,-19.30000,0.00000),V(54.17000,-19.30000,0.00000),V(54.17000,-18.90000,0.00000),V(54.57000,-18.90000,0.00000),V(54.57000,-19.30000,0.00000),V(54.52000,-19.30000,0.00000),V(54.52000,-19.85000,0.00000),V(55.12000,-19.85000,0.00000),V(55.12000,-20.75000,0.00000),V(54.22000,-20.75000,0.00000),V(54.22000,-20.30000,0.00000),V(54.22000,-19.85000,0.00000),V(54.22000,-19.30000,0.00000)])]).extrude(V(0,0,0.01200)))
_s.append(Part.Face([_poly([V(52.43700,-4.49200,0.00000),V(52.43700,-4.44200,0.00000),V(50.61500,-4.44200,0.00000),V(50.61500,-2.15000,0.00000),V(51.68000,-2.15000,0.00000),V(51.68000,-1.85000,0.00000),V(52.58000,-1.85000,0.00000),V(52.58000,-2.75000,0.00000),V(51.68000,-2.75000,0.00000),V(51.68000,-2.45000,0.00000),V(50.91500,-2.45000,0.00000),V(50.91500,-4.14200,0.00000),V(52.43700,-4.14200,0.00000),V(52.43700,-4.09200,0.00000),V(52.83700,-4.09200,0.00000),V(52.83700,-4.49200,0.00000),V(52.43700,-4.49200,0.00000)])]).extrude(V(0,0,0.01200)))
_s.append(Part.Face([_poly([V(49.44000,-2.75000,0.00000),V(49.14000,-2.75000,0.00000),V(49.14000,-1.85000,0.00000),V(50.04000,-1.85000,0.00000),V(50.04000,-2.75000,0.00000),V(49.74000,-2.75000,0.00000),V(49.74000,-3.21000,0.00000),V(49.99700,-3.21000,0.00000),V(49.99700,-3.61000,0.00000),V(49.59700,-3.61000,0.00000),V(49.59700,-3.56000,0.00000),V(49.44000,-3.56000,0.00000),V(49.44000,-2.75000,0.00000)])]).extrude(V(0,0,0.01200)))
_s.append(Part.Face([_poly([V(52.88200,-3.21900,0.00000),V(52.88200,-2.15000,0.00000),V(54.22000,-2.15000,0.00000),V(54.22000,-1.85000,0.00000),V(55.12000,-1.85000,0.00000),V(55.12000,-2.75000,0.00000),V(54.22000,-2.75000,0.00000),V(54.22000,-2.45000,0.00000),V(53.18200,-2.45000,0.00000),V(53.18200,-3.21900,0.00000),V(53.18200,-3.53800,0.00000),V(51.92600,-3.53800,0.00000),V(51.92600,-3.58800,0.00000),V(51.52600,-3.58800,0.00000),V(51.52600,-3.18800,0.00000),V(51.92600,-3.18800,0.00000),V(51.92600,-3.23800,0.00000),V(52.88200,-3.23800,0.00000),V(52.88200,-3.21900,0.00000)])]).extrude(V(0,0,0.01200)))
_s.append(Part.Face([_poly([V(65.28000,-20.75000,0.00000),V(64.38000,-20.75000,0.00000),V(64.38000,-19.85000,0.00000),V(65.28000,-19.85000,0.00000),V(65.28000,-20.75000,0.00000)])]).extrude(V(0,0,0.01200)))
_s.append(Part.Face([_poly([V(59.30000,-18.00000,0.00000),V(59.25000,-18.00000,0.00000),V(59.25000,-17.60000,0.00000),V(59.65000,-17.60000,0.00000),V(59.65000,-18.00000,0.00000),V(59.60000,-18.00000,0.00000),V(59.60000,-19.85000,0.00000),V(60.20000,-19.85000,0.00000),V(60.20000,-20.75000,0.00000),V(59.30000,-20.75000,0.00000),V(59.30000,-20.30000,0.00000),V(59.30000,-19.85000,0.00000),V(59.30000,-18.00000,0.00000)])]).extrude(V(0,0,0.01200)))
_s.append(Part.Face([_poly([V(55.37200,-19.45000,0.00000),V(55.37200,-19.05000,0.00000),V(55.77200,-19.05000,0.00000),V(55.77200,-19.45000,0.00000),V(55.72200,-19.45000,0.00000),V(55.72200,-20.15000,0.00000),V(56.76000,-20.15000,0.00000),V(56.76000,-19.85000,0.00000),V(57.66000,-19.85000,0.00000),V(57.66000,-20.75000,0.00000),V(56.76000,-20.75000,0.00000),V(56.76000,-20.45000,0.00000),V(55.42200,-20.45000,0.00000),V(55.42200,-19.45000,0.00000),V(55.37200,-19.45000,0.00000)])]).extrude(V(0,0,0.01200)))
_s.append(Part.Face([_poly([V(61.84000,-20.75000,0.00000),V(61.84000,-19.85000,0.00000),V(62.74000,-19.85000,0.00000),V(62.74000,-20.75000,0.00000),V(61.84000,-20.75000,0.00000)])]).extrude(V(0,0,0.01200)))
_s.append(Part.Face([_poly([V(59.29800,-3.05900,0.00000),V(59.29800,-2.15000,0.00000),V(59.30000,-2.15000,0.00000),V(59.30000,-1.85000,0.00000),V(60.20000,-1.85000,0.00000),V(60.20000,-2.75000,0.00000),V(59.59800,-2.75000,0.00000),V(59.59800,-3.05900,0.00000),V(59.59800,-3.06900,0.00000),V(60.50200,-3.06900,0.00000),V(60.50200,-2.15000,0.00000),V(61.84000,-2.15000,0.00000),V(61.84000,-1.85000,0.00000),V(62.74000,-1.85000,0.00000),V(62.74000,-2.75000,0.00000),V(61.84000,-2.75000,0.00000),V(61.84000,-2.45000,0.00000),V(60.80200,-2.45000,0.00000),V(60.80200,-3.21900,0.00000),V(60.80128,-3.23370,0.00000),V(60.79912,-3.24826,0.00000),V(60.79554,-3.26254,0.00000),V(60.79058,-3.27640,0.00000),V(60.78429,-3.28971,0.00000),V(60.77672,-3.30234,0.00000),V(60.76795,-3.31416,0.00000),V(60.75807,-3.32507,0.00000),V(60.74716,-3.33495,0.00000),V(60.73534,-3.34372,0.00000),V(60.72271,-3.35129,0.00000),V(60.70940,-3.35758,0.00000),V(60.69554,-3.36254,0.00000),V(60.68126,-3.36612,0.00000),V(60.66670,-3.36828,0.00000),V(60.65200,-3.36900,0.00000),V(60.22000,-3.36900,0.00000),V(60.22000,-3.58100,0.00000),V(59.82000,-3.58100,0.00000),V(59.82000,-3.53100,0.00000),V(59.29800,-3.53100,0.00000),V(59.29800,-3.21900,0.00000),V(59.29800,-3.05900,0.00000)])]).extrude(V(0,0,0.01200)))
_s.append(Part.Face([_poly([V(56.76000,-2.15000,0.00000),V(56.76000,-1.85000,0.00000),V(57.66000,-1.85000,0.00000),V(57.66000,-2.75000,0.00000),V(56.76000,-2.75000,0.00000),V(56.76000,-2.45000,0.00000),V(56.39000,-2.45000,0.00000),V(56.39000,-3.08200,0.00000),V(56.44000,-3.08200,0.00000),V(56.44000,-3.48200,0.00000),V(56.04000,-3.48200,0.00000),V(56.04000,-3.08200,0.00000),V(56.09000,-3.08200,0.00000),V(56.09000,-2.15000,0.00000),V(56.76000,-2.15000,0.00000)])]).extrude(V(0,0,0.01200)))
_add('1st Routing Conductor' + '_L3', _fuse(_s), (1.0000,0.5020,0.2510), surface=True)
# --- layer 4 (Routing Dielectric) : z 0.0120..0.0420 mm ---
_s = []
_s.append(Part.Face([_poly([V(33.52600,-20.15000,0.01200),V(27.81100,-20.15000,0.01200),V(16.72000,-20.15000,0.01200),V(16.72000,-18.30000,0.01200),V(16.72000,-4.95000,0.01200),V(16.72000,-2.45000,0.01200),V(22.52000,-2.45000,0.01200),V(25.99000,-2.45000,0.01200),V(29.79100,-2.45000,0.01200),V(56.24000,-2.45000,0.01200),V(58.99500,-2.45000,0.01200),V(64.68000,-2.45000,0.01200),V(64.68000,-3.38100,0.01200),V(64.68000,-10.24300,0.01200),V(64.68000,-11.25200,0.01200),V(64.68000,-20.15000,0.01200),V(55.57200,-20.15000,0.01200),V(54.37000,-20.15000,0.01200),V(33.52600,-20.15000,0.01200)]), _poly([V(41.70300,-19.50700,0.01200),V(42.30300,-19.50700,0.01200),V(42.30300,-19.20700,0.01200),V(42.30300,-18.90700,0.01200),V(41.70300,-18.90700,0.01200),V(41.70300,-19.20700,0.01200),V(41.70300,-19.50700,0.01200)]), _poly([V(45.82200,-19.37800,0.01200),V(46.42200,-19.37800,0.01200),V(46.42200,-19.20600,0.01200),V(46.42200,-18.77800,0.01200),V(46.12200,-18.77800,0.01200),V(45.82200,-18.77800,0.01200),V(45.82200,-19.20700,0.01200),V(45.82200,-19.37800,0.01200)]), _poly([V(47.19500,-19.50600,0.01200),V(47.79500,-19.50600,0.01200),V(47.79500,-19.20600,0.01200),V(47.79500,-18.90600,0.01200),V(47.19500,-18.90600,0.01200),V(47.19500,-19.20600,0.01200),V(47.19500,-19.50600,0.01200)]), _poly([V(49.02000,-19.32500,0.01200),V(49.02000,-19.92500,0.01200),V(49.62000,-19.92500,0.01200),V(49.62000,-19.70000,0.01200),V(49.62000,-19.32500,0.01200),V(49.32000,-19.32500,0.01200),V(49.02000,-19.32500,0.01200)]), _poly([V(51.44500,-20.00000,0.01200),V(52.04500,-20.00000,0.01200),V(52.04500,-19.70000,0.01200),V(52.04500,-19.40000,0.01200),V(51.44500,-19.40000,0.01200),V(51.44500,-19.70000,0.01200),V(51.44500,-20.00000,0.01200)]), _poly([V(54.07000,-18.80000,0.01200),V(54.07000,-19.40000,0.01200),V(54.37000,-19.40000,0.01200),V(54.67000,-19.40000,0.01200),V(54.67000,-18.80000,0.01200),V(54.37000,-18.80000,0.01200),V(54.07000,-18.80000,0.01200)]), _poly([V(29.49100,-3.08400,0.01200),V(29.49100,-3.68400,0.01200),V(29.79100,-3.68400,0.01200),V(30.09100,-3.68400,0.01200),V(30.09100,-3.08400,0.01200),V(29.79100,-3.08400,0.01200),V(29.49100,-3.08400,0.01200)]), _poly([V(31.82000,-7.77500,0.01200),V(32.42000,-7.77500,0.01200),V(32.42000,-7.47500,0.01200),V(32.42000,-7.17500,0.01200),V(31.82000,-7.17500,0.01200),V(31.82000,-7.47500,0.01200),V(31.82000,-7.77500,0.01200)]), _poly([V(35.84500,-7.36600,0.01200),V(35.84500,-6.76600,0.01200),V(35.54500,-6.76600,0.01200),V(35.24500,-6.76600,0.01200),V(35.24500,-7.36600,0.01200),V(35.54500,-7.36600,0.01200),V(35.84500,-7.36600,0.01200)]), _poly([V(35.89700,-5.35900,0.01200),V(35.89700,-4.75900,0.01200),V(35.54500,-4.75900,0.01200),V(35.29700,-4.75900,0.01200),V(35.29700,-5.35900,0.01200),V(35.54500,-5.35900,0.01200),V(35.89700,-5.35900,0.01200)]), _poly([V(36.09500,-3.67800,0.01200),V(36.69500,-3.67800,0.01200),V(36.69500,-3.40900,0.01200),V(36.69500,-3.07800,0.01200),V(36.09500,-3.07800,0.01200),V(36.09500,-3.40900,0.01200),V(36.09500,-3.67800,0.01200)]), _poly([V(39.04800,-3.70900,0.01200),V(39.64800,-3.70900,0.01200),V(39.64800,-3.40900,0.01200),V(39.64800,-3.10900,0.01200),V(39.04800,-3.10900,0.01200),V(39.04800,-3.40900,0.01200),V(39.04800,-3.70900,0.01200)]), _poly([V(40.07800,-3.83600,0.01200),V(40.07800,-4.43600,0.01200),V(40.37800,-4.43600,0.01200),V(40.67800,-4.43600,0.01200),V(40.67800,-3.83600,0.01200),V(40.37800,-3.83600,0.01200),V(40.07800,-3.83600,0.01200)]), _poly([V(41.73500,-8.21800,0.01200),V(42.33500,-8.21800,0.01200),V(42.33500,-7.91800,0.01200),V(42.33500,-7.61800,0.01200),V(41.73500,-7.61800,0.01200),V(41.73500,-7.91800,0.01200),V(41.73500,-8.21800,0.01200)]), _poly([V(42.99900,-8.39100,0.01200),V(42.99900,-8.99100,0.01200),V(43.29900,-8.99100,0.01200),V(43.59900,-8.99100,0.01200),V(43.59900,-8.39100,0.01200),V(43.29900,-8.39100,0.01200),V(42.99900,-8.39100,0.01200)]), _poly([V(39.20500,-9.95600,0.01200),V(38.60500,-9.95600,0.01200),V(38.60500,-10.25600,0.01200),V(38.60500,-10.55600,0.01200),V(39.20500,-10.55600,0.01200),V(39.20500,-10.25600,0.01200),V(39.20500,-9.95600,0.01200)]), _poly([V(31.94400,-12.42500,0.01200),V(31.94400,-13.02500,0.01200),V(32.24400,-13.02500,0.01200),V(32.54400,-13.02500,0.01200),V(32.54400,-12.42500,0.01200),V(32.24400,-12.42500,0.01200),V(31.94400,-12.42500,0.01200)]), _poly([V(39.13000,-16.46600,0.01200),V(39.73000,-16.46600,0.01200),V(39.73000,-16.16600,0.01200),V(39.73000,-15.86600,0.01200),V(39.13000,-15.86600,0.01200),V(39.13000,-16.16600,0.01200),V(39.13000,-16.46600,0.01200)]), _poly([V(19.71000,-18.60000,0.01200),V(19.71000,-18.30000,0.01200),V(19.71000,-18.00000,0.01200),V(19.11000,-18.00000,0.01200),V(19.11000,-18.30000,0.01200),V(19.11000,-18.60000,0.01200),V(19.71000,-18.60000,0.01200)]), _poly([V(20.87000,-17.25000,0.01200),V(20.57000,-17.25000,0.01200),V(20.27000,-17.25000,0.01200),V(20.27000,-17.85000,0.01200),V(20.57000,-17.85000,0.01200),V(20.87000,-17.85000,0.01200),V(20.87000,-17.25000,0.01200)]), _poly([V(24.02000,-13.70000,0.01200),V(24.02000,-13.40000,0.01200),V(24.02000,-13.10000,0.01200),V(23.42000,-13.10000,0.01200),V(23.42000,-13.40000,0.01200),V(23.42000,-13.70000,0.01200),V(24.02000,-13.70000,0.01200)]), _poly([V(31.61800,-16.10800,0.01200),V(31.61800,-15.80800,0.01200),V(31.61800,-15.50800,0.01200),V(31.01800,-15.50800,0.01200),V(31.01800,-15.80800,0.01200),V(31.01800,-16.10800,0.01200),V(31.61800,-16.10800,0.01200)]), _poly([V(36.39300,-18.92200,0.01200),V(35.79300,-18.92200,0.01200),V(35.79300,-19.22200,0.01200),V(35.79300,-19.52200,0.01200),V(36.39300,-19.52200,0.01200),V(36.39300,-19.22200,0.01200),V(36.39300,-18.92200,0.01200)]), _poly([V(37.54500,-19.19000,0.01200),V(37.54500,-18.92200,0.01200),V(36.94500,-18.92200,0.01200),V(36.94500,-19.22200,0.01200),V(36.94500,-19.52200,0.01200),V(37.54500,-19.52200,0.01200),V(37.54500,-19.19000,0.01200)]), _poly([V(39.73000,-19.19000,0.01200),V(39.73000,-18.89000,0.01200),V(39.13000,-18.89000,0.01200),V(39.13000,-19.19000,0.01200),V(39.13000,-19.49000,0.01200),V(39.73000,-19.49000,0.01200),V(39.73000,-19.19000,0.01200)]), _poly([V(33.82600,-18.88800,0.01200),V(33.22600,-18.88800,0.01200),V(33.22600,-19.48800,0.01200),V(33.52600,-19.48800,0.01200),V(33.82600,-19.48800,0.01200),V(33.82600,-19.22200,0.01200),V(33.82600,-18.88800,0.01200)]), _poly([V(24.80800,-16.10800,0.01200),V(24.80800,-15.50800,0.01200),V(24.50800,-15.50800,0.01200),V(24.20800,-15.50800,0.01200),V(24.20800,-16.10800,0.01200),V(24.50800,-16.10800,0.01200),V(24.80800,-16.10800,0.01200)]), _poly([V(26.12800,-18.95000,0.01200),V(25.52800,-18.95000,0.01200),V(25.52800,-19.25000,0.01200),V(25.52800,-19.55000,0.01200),V(26.12800,-19.55000,0.01200),V(26.12800,-19.25000,0.01200),V(26.12800,-18.95000,0.01200)]), _poly([V(28.11100,-18.91600,0.01200),V(27.51100,-18.91600,0.01200),V(27.51100,-19.25000,0.01200),V(27.51100,-19.51600,0.01200),V(27.81100,-19.51600,0.01200),V(28.11100,-19.51600,0.01200),V(28.11100,-18.91600,0.01200)]), _poly([V(20.42000,-4.95000,0.01200),V(20.42000,-4.65000,0.01200),V(19.82000,-4.65000,0.01200),V(19.82000,-4.95000,0.01200),V(19.82000,-5.25000,0.01200),V(20.42000,-5.25000,0.01200),V(20.42000,-4.95000,0.01200)]), _poly([V(24.82000,-8.80000,0.01200),V(24.82000,-8.50000,0.01200),V(24.22000,-8.50000,0.01200),V(24.22000,-8.80000,0.01200),V(24.22000,-9.10000,0.01200),V(24.82000,-9.10000,0.01200),V(24.82000,-8.80000,0.01200)]), _poly([V(26.12000,-5.80000,0.01200),V(26.12000,-6.10000,0.01200),V(26.72000,-6.10000,0.01200),V(26.72000,-5.80000,0.01200),V(26.72000,-5.50000,0.01200),V(26.12000,-5.50000,0.01200),V(26.12000,-5.80000,0.01200)]), _poly([V(25.99000,-3.09700,0.01200),V(25.69000,-3.09700,0.01200),V(25.69000,-3.69700,0.01200),V(25.99000,-3.69700,0.01200),V(26.29000,-3.69700,0.01200),V(26.29000,-3.09700,0.01200),V(25.99000,-3.09700,0.01200)]), _poly([V(22.22000,-3.90000,0.01200),V(22.22000,-4.50000,0.01200),V(22.52000,-4.50000,0.01200),V(22.82000,-4.50000,0.01200),V(22.82000,-3.90000,0.01200),V(22.52000,-3.90000,0.01200),V(22.22000,-3.90000,0.01200)]), _poly([V(46.11800,-11.16700,0.01200),V(46.11800,-10.86700,0.01200),V(46.11800,-10.56700,0.01200),V(45.51800,-10.56700,0.01200),V(45.51800,-10.86700,0.01200),V(45.51800,-11.16700,0.01200),V(46.11800,-11.16700,0.01200)]), _poly([V(54.32000,-9.90000,0.01200),V(54.02000,-9.90000,0.01200),V(53.72000,-9.90000,0.01200),V(53.72000,-10.50000,0.01200),V(54.02000,-10.50000,0.01200),V(54.32000,-10.50000,0.01200),V(54.32000,-9.90000,0.01200)]), _poly([V(53.12600,-9.07000,0.01200),V(53.12600,-9.37000,0.01200),V(53.12600,-9.67000,0.01200),V(53.72600,-9.67000,0.01200),V(53.72600,-9.37000,0.01200),V(53.72600,-9.07000,0.01200),V(53.12600,-9.07000,0.01200)]), _poly([V(50.43000,-8.12100,0.01200),V(50.43000,-8.42100,0.01200),V(50.43000,-8.72100,0.01200),V(51.03000,-8.72100,0.01200),V(51.03000,-8.42100,0.01200),V(51.03000,-8.12100,0.01200),V(50.43000,-8.12100,0.01200)]), _poly([V(49.34200,-7.53100,0.01200),V(49.04200,-7.53100,0.01200),V(48.74200,-7.53100,0.01200),V(48.74200,-8.13100,0.01200),V(49.04200,-8.13100,0.01200),V(49.34200,-8.13100,0.01200),V(49.34200,-7.53100,0.01200)]), _poly([V(52.02600,-6.30900,0.01200),V(52.02600,-6.00900,0.01200),V(52.02600,-5.70900,0.01200),V(51.42600,-5.70900,0.01200),V(51.42600,-6.00900,0.01200),V(51.42600,-6.30900,0.01200),V(52.02600,-6.30900,0.01200)]), _poly([V(52.93700,-3.99200,0.01200),V(52.63700,-3.99200,0.01200),V(52.33700,-3.99200,0.01200),V(52.33700,-4.59200,0.01200),V(52.63700,-4.59200,0.01200),V(52.93700,-4.59200,0.01200),V(52.93700,-3.99200,0.01200)]), _poly([V(51.42600,-3.08800,0.01200),V(51.42600,-3.38800,0.01200),V(51.42600,-3.68800,0.01200),V(52.02600,-3.68800,0.01200),V(52.02600,-3.38800,0.01200),V(52.02600,-3.08800,0.01200),V(51.42600,-3.08800,0.01200)]), _poly([V(49.49700,-3.11000,0.01200),V(49.49700,-3.40200,0.01200),V(49.49700,-3.71000,0.01200),V(50.09700,-3.71000,0.01200),V(50.09700,-3.38800,0.01200),V(50.09700,-3.11000,0.01200),V(49.49700,-3.11000,0.01200)]), _poly([V(47.94700,-3.10200,0.01200),V(47.94700,-3.40200,0.01200),V(47.94700,-3.70200,0.01200),V(48.54700,-3.70200,0.01200),V(48.54700,-3.40200,0.01200),V(48.54700,-3.10200,0.01200),V(47.94700,-3.10200,0.01200)]), _poly([V(45.95900,-3.06800,0.01200),V(45.95900,-3.66800,0.01200),V(46.25900,-3.66800,0.01200),V(46.55900,-3.66800,0.01200),V(46.55900,-3.40200,0.01200),V(46.55900,-3.06800,0.01200),V(45.95900,-3.06800,0.01200)]), _poly([V(44.04000,-5.53000,0.01200),V(44.04000,-5.83000,0.01200),V(44.04000,-6.13000,0.01200),V(44.64000,-6.13000,0.01200),V(44.64000,-5.83000,0.01200),V(44.64000,-5.53000,0.01200),V(44.04000,-5.53000,0.01200)]), _poly([V(55.94000,-3.58200,0.01200),V(56.24000,-3.58200,0.01200),V(56.54000,-3.58200,0.01200),V(56.54000,-2.98200,0.01200),V(56.24000,-2.98200,0.01200),V(55.94000,-2.98200,0.01200),V(55.94000,-3.58200,0.01200)]), _poly([V(56.21900,-6.41100,0.01200),V(56.81900,-6.41100,0.01200),V(56.81900,-6.11100,0.01200),V(56.81900,-5.81100,0.01200),V(56.24000,-5.81100,0.01200),V(56.21900,-5.81100,0.01200),V(56.21900,-6.41100,0.01200)]), _poly([V(58.69500,-9.38400,0.01200),V(58.99500,-9.38400,0.01200),V(59.29500,-9.38400,0.01200),V(59.29500,-8.78400,0.01200),V(58.99500,-8.78400,0.01200),V(58.69500,-8.78400,0.01200),V(58.69500,-9.38400,0.01200)]), _poly([V(60.32000,-10.54300,0.01200),V(60.32000,-10.24300,0.01200),V(60.32000,-9.94300,0.01200),V(59.72000,-9.94300,0.01200),V(59.72000,-10.24300,0.01200),V(59.72000,-10.54300,0.01200),V(60.32000,-10.54300,0.01200)]), _poly([V(47.19300,-16.74800,0.01200),V(47.19300,-16.44800,0.01200),V(46.59300,-16.44800,0.01200),V(46.59300,-16.74800,0.01200),V(46.59300,-17.04800,0.01200),V(47.19300,-17.04800,0.01200),V(47.19300,-16.74800,0.01200)]), _poly([V(50.34500,-15.98100,0.01200),V(50.34500,-15.68100,0.01200),V(49.74500,-15.68100,0.01200),V(49.74500,-15.98100,0.01200),V(49.74500,-16.28100,0.01200),V(50.34500,-16.28100,0.01200),V(50.34500,-15.98100,0.01200)]), _poly([V(55.27200,-18.95000,0.01200),V(55.27200,-19.55000,0.01200),V(55.57200,-19.55000,0.01200),V(55.87200,-19.55000,0.01200),V(55.87200,-18.95000,0.01200),V(55.57200,-18.95000,0.01200),V(55.27200,-18.95000,0.01200)]), _poly([V(57.47000,-17.83200,0.01200),V(56.87000,-17.83200,0.01200),V(56.87000,-18.13200,0.01200),V(56.87000,-18.43200,0.01200),V(57.47000,-18.43200,0.01200),V(57.47000,-18.13200,0.01200),V(57.47000,-17.83200,0.01200)]), _poly([V(59.15000,-17.50000,0.01200),V(59.15000,-18.10000,0.01200),V(59.45000,-18.10000,0.01200),V(59.75000,-18.10000,0.01200),V(59.75000,-17.50000,0.01200),V(59.45000,-17.50000,0.01200),V(59.15000,-17.50000,0.01200)]), _poly([V(62.08400,-11.00200,0.01200),V(61.58400,-11.00200,0.01200),V(61.58400,-11.25200,0.01200),V(61.58400,-11.50200,0.01200),V(62.08400,-11.50200,0.01200),V(62.08400,-11.25200,0.01200),V(62.08400,-11.00200,0.01200)]), _poly([V(60.32000,-3.08100,0.01200),V(59.72000,-3.08100,0.01200),V(59.72000,-3.38100,0.01200),V(59.72000,-3.68100,0.01200),V(60.32000,-3.68100,0.01200),V(60.32000,-3.38100,0.01200),V(60.32000,-3.08100,0.01200)]), _poly([V(63.49200,-3.08100,0.01200),V(62.89200,-3.08100,0.01200),V(62.89200,-3.38100,0.01200),V(62.89200,-3.68100,0.01200),V(63.49200,-3.68100,0.01200),V(63.49200,-3.38100,0.01200),V(63.49200,-3.08100,0.01200)])]).extrude(V(0,0,0.03000)))
_add('Routing Dielectric' + '_L4', _fuse(_s), (0.5020,0.5020,1.0000), surface=True)
# --- layer 5 (2nd Routing Conductor) : z 0.0420..0.0540 mm ---
_s = []
_s.append(Part.Face([_poly([V(22.52000,-17.20000,0.04200),V(22.37000,-17.20000,0.04200),V(22.22000,-17.20000,0.04200),V(22.22000,-17.05000,0.04200),V(22.22000,-16.90000,0.04200),V(22.37000,-16.90000,0.04200),V(22.52000,-16.90000,0.04200),V(25.97800,-16.90000,0.04200),V(25.97800,-19.05000,0.04200),V(26.02800,-19.05000,0.04200),V(26.02800,-19.45000,0.04200),V(25.62800,-19.45000,0.04200),V(25.62800,-19.05000,0.04200),V(25.67800,-19.05000,0.04200),V(25.67800,-17.20000,0.04200),V(22.52000,-17.20000,0.04200)])]).extrude(V(0,0,0.01200)))
_s.append(Part.Face([_poly([V(19.07000,-16.35000,0.04200),V(19.07000,-16.30000,0.04200),V(19.07000,-16.15000,0.04200),V(19.07000,-16.00000,0.04200),V(19.22000,-16.00000,0.04200),V(19.37000,-16.00000,0.04200),V(19.37000,-16.05000,0.04200),V(19.56000,-16.05000,0.04200),V(19.56000,-18.10000,0.04200),V(19.61000,-18.10000,0.04200),V(19.61000,-18.50000,0.04200),V(19.21000,-18.50000,0.04200),V(19.21000,-18.10000,0.04200),V(19.26000,-18.10000,0.04200),V(19.26000,-16.35000,0.04200),V(19.07000,-16.35000,0.04200)])]).extrude(V(0,0,0.01200)))
_s.append(Part.Face([_poly([V(20.42000,-17.05000,0.04200),V(20.42000,-16.90000,0.04200),V(20.57000,-16.90000,0.04200),V(20.72000,-16.90000,0.04200),V(20.72000,-17.05000,0.04200),V(20.72000,-17.20000,0.04200),V(20.72000,-17.35000,0.04200),V(20.77000,-17.35000,0.04200),V(20.77000,-17.75000,0.04200),V(20.37000,-17.75000,0.04200),V(20.37000,-17.35000,0.04200),V(20.42000,-17.35000,0.04200),V(20.42000,-17.20000,0.04200),V(20.42000,-17.05000,0.04200)])]).extrude(V(0,0,0.01200)))
_s.append(Part.Face([_poly([V(24.70800,-16.00800,0.04200),V(24.30800,-16.00800,0.04200),V(24.30800,-15.95800,0.04200),V(23.87000,-15.95800,0.04200),V(23.87000,-16.00000,0.04200),V(23.87000,-16.15000,0.04200),V(23.87000,-16.30000,0.04200),V(23.72000,-16.30000,0.04200),V(23.57000,-16.30000,0.04200),V(23.57000,-16.15000,0.04200),V(23.57000,-16.00000,0.04200),V(23.57000,-15.80800,0.04200),V(23.57000,-15.40000,0.04200),V(23.57000,-15.25000,0.04200),V(23.57000,-15.10000,0.04200),V(23.72000,-15.10000,0.04200),V(23.87000,-15.10000,0.04200),V(23.87000,-15.25000,0.04200),V(23.87000,-15.40000,0.04200),V(23.87000,-15.65800,0.04200),V(24.30800,-15.65800,0.04200),V(24.30800,-15.60800,0.04200),V(24.70800,-15.60800,0.04200),V(24.70800,-16.00800,0.04200)])]).extrude(V(0,0,0.01200)))
_s.append(Part.Face([_poly([V(19.07000,-13.45000,0.04200),V(19.07000,-13.30000,0.04200),V(19.07000,-12.40000,0.04200),V(21.32000,-12.40000,0.04200),V(21.47000,-12.40000,0.04200),V(21.62000,-12.40000,0.04200),V(21.62000,-12.55000,0.04200),V(21.62000,-12.70000,0.04200),V(21.47000,-12.70000,0.04200),V(21.32000,-12.70000,0.04200),V(19.37000,-12.70000,0.04200),V(19.37000,-13.30000,0.04200),V(19.37000,-13.45000,0.04200),V(19.37000,-13.60000,0.04200),V(19.37000,-15.10000,0.04200),V(19.37000,-15.25000,0.04200),V(19.37000,-15.40000,0.04200),V(19.22000,-15.40000,0.04200),V(19.07000,-15.40000,0.04200),V(19.07000,-15.25000,0.04200),V(19.07000,-15.10000,0.04200),V(19.07000,-13.60000,0.04200),V(19.07000,-13.45000,0.04200)])]).extrude(V(0,0,0.01200)))
_s.append(Part.Face([_poly([V(20.52000,-15.75000,0.04200),V(20.52000,-13.85000,0.04200),V(22.42000,-13.85000,0.04200),V(22.42000,-15.75000,0.04200),V(20.52000,-15.75000,0.04200)])]).extrude(V(0,0,0.01200)))
_s.append(Part.Face([_poly([V(23.57000,-13.60000,0.04200),V(23.52000,-13.60000,0.04200),V(23.52000,-13.20000,0.04200),V(23.92000,-13.20000,0.04200),V(23.92000,-13.60000,0.04200),V(23.87000,-13.60000,0.04200),V(23.57000,-13.60000,0.04200)])]).extrude(V(0,0,0.01200)))
_s.append(Part.Face([_poly([V(22.22000,-10.47500,0.04200),V(21.61200,-10.47500,0.04200),V(21.61200,-6.90000,0.04200),V(21.47000,-6.90000,0.04200),V(21.47000,-6.75000,0.04200),V(21.47000,-6.60000,0.04200),V(21.62000,-6.60000,0.04200),V(21.77000,-6.60000,0.04200),V(21.91200,-6.60000,0.04200),V(21.91200,-10.17500,0.04200),V(22.52000,-10.17500,0.04200),V(22.52000,-12.40000,0.04200),V(22.52000,-12.55000,0.04200),V(22.52000,-12.70000,0.04200),V(22.37000,-12.70000,0.04200),V(22.22000,-12.70000,0.04200),V(22.22000,-12.55000,0.04200),V(22.22000,-12.40000,0.04200),V(22.22000,-10.47500,0.04200)])]).extrude(V(0,0,0.01200)))
_s.append(Part.Face([_poly([V(24.32000,-9.00000,0.04200),V(24.32000,-8.95000,0.04200),V(22.37000,-8.95000,0.04200),V(22.37000,-8.25000,0.04200),V(22.37000,-8.10000,0.04200),V(22.37000,-7.95000,0.04200),V(22.52000,-7.95000,0.04200),V(22.67000,-7.95000,0.04200),V(22.67000,-8.10000,0.04200),V(22.67000,-8.25000,0.04200),V(22.67000,-8.65000,0.04200),V(24.32000,-8.65000,0.04200),V(24.32000,-8.60000,0.04200),V(24.72000,-8.60000,0.04200),V(24.72000,-9.00000,0.04200),V(24.32000,-9.00000,0.04200)])]).extrude(V(0,0,0.01200)))
_s.append(Part.Face([_poly([V(23.27000,-4.37500,0.04200),V(23.27000,-3.75000,0.04200),V(23.27000,-3.60000,0.04200),V(23.27000,-3.45000,0.04200),V(23.42000,-3.45000,0.04200),V(23.57000,-3.45000,0.04200),V(23.57000,-3.60000,0.04200),V(23.57000,-3.75000,0.04200),V(23.57000,-4.07500,0.04200),V(25.64500,-4.07500,0.04200),V(25.64500,-7.32500,0.04200),V(31.92000,-7.32500,0.04200),V(31.92000,-7.27500,0.04200),V(32.32000,-7.27500,0.04200),V(32.32000,-7.67500,0.04200),V(32.27000,-7.67500,0.04200),V(32.27000,-9.17500,0.04200),V(32.27000,-9.32500,0.04200),V(32.27000,-9.47500,0.04200),V(32.12000,-9.47500,0.04200),V(31.97000,-9.47500,0.04200),V(31.97000,-9.32500,0.04200),V(31.97000,-9.17500,0.04200),V(31.97000,-7.67500,0.04200),V(31.92000,-7.67500,0.04200),V(31.92000,-7.62500,0.04200),V(25.49500,-7.62500,0.04200),V(23.57000,-7.62500,0.04200),V(23.57000,-7.95000,0.04200),V(23.57000,-8.10000,0.04200),V(23.57000,-8.25000,0.04200),V(23.42000,-8.25000,0.04200),V(23.27000,-8.25000,0.04200),V(23.27000,-8.10000,0.04200),V(23.27000,-7.95000,0.04200),V(23.27000,-7.32500,0.04200),V(25.34500,-7.32500,0.04200),V(25.34500,-4.37500,0.04200),V(23.27000,-4.37500,0.04200)])]).extrude(V(0,0,0.01200)))
_s.append(Part.Face([_poly([V(25.07000,-8.25000,0.04200),V(25.07000,-8.10000,0.04200),V(25.07000,-7.95000,0.04200),V(25.22000,-7.95000,0.04200),V(25.37000,-7.95000,0.04200),V(27.96100,-7.95000,0.04200),V(27.96100,-16.71200,0.04200),V(31.97000,-16.71200,0.04200),V(31.97000,-13.72500,0.04200),V(31.97000,-13.57500,0.04200),V(31.97000,-13.42500,0.04200),V(32.12000,-13.42500,0.04200),V(32.27000,-13.42500,0.04200),V(32.27000,-13.57500,0.04200),V(32.27000,-13.72500,0.04200),V(32.27000,-17.01200,0.04200),V(27.96100,-17.01200,0.04200),V(27.96100,-19.01600,0.04200),V(28.01100,-19.01600,0.04200),V(28.01100,-19.41600,0.04200),V(27.61100,-19.41600,0.04200),V(27.61100,-19.01600,0.04200),V(27.66100,-19.01600,0.04200),V(27.66100,-16.86200,0.04200),V(27.66100,-8.25000,0.04200),V(25.37000,-8.25000,0.04200),V(25.22000,-8.25000,0.04200),V(25.07000,-8.25000,0.04200)])]).extrude(V(0,0,0.01200)))
_s.append(Part.Face([_poly([V(22.92000,-4.90000,0.04200),V(24.82000,-4.90000,0.04200),V(24.82000,-6.80000,0.04200),V(22.92000,-6.80000,0.04200),V(22.92000,-4.90000,0.04200)])]).extrude(V(0,0,0.01200)))
_s.append(Part.Face([_poly([V(21.77000,-5.10000,0.04200),V(21.62000,-5.10000,0.04200),V(21.47000,-5.10000,0.04200),V(20.32000,-5.10000,0.04200),V(20.32000,-5.15000,0.04200),V(19.92000,-5.15000,0.04200),V(19.92000,-4.75000,0.04200),V(20.32000,-4.75000,0.04200),V(20.32000,-4.80000,0.04200),V(21.47000,-4.80000,0.04200),V(21.62000,-4.80000,0.04200),V(21.77000,-4.80000,0.04200),V(21.77000,-4.95000,0.04200),V(21.77000,-5.10000,0.04200)])]).extrude(V(0,0,0.01200)))
_s.append(Part.Face([_poly([V(22.37000,-3.45000,0.04200),V(22.52000,-3.45000,0.04200),V(22.67000,-3.45000,0.04200),V(22.67000,-3.60000,0.04200),V(22.67000,-3.75000,0.04200),V(22.67000,-4.00000,0.04200),V(22.72000,-4.00000,0.04200),V(22.72000,-4.40000,0.04200),V(22.32000,-4.40000,0.04200),V(22.32000,-4.00000,0.04200),V(22.37000,-4.00000,0.04200),V(22.37000,-3.75000,0.04200),V(22.37000,-3.60000,0.04200),V(22.37000,-3.45000,0.04200)])]).extrude(V(0,0,0.01200)))
_s.append(Part.Face([_poly([V(25.37000,-3.60000,0.04200),V(25.37000,-3.75000,0.04200),V(25.22000,-3.75000,0.04200),V(25.07000,-3.75000,0.04200),V(25.07000,-3.60000,0.04200),V(25.07000,-3.45000,0.04200),V(25.07000,-3.24700,0.04200),V(25.79000,-3.24700,0.04200),V(25.79000,-3.19700,0.04200),V(26.19000,-3.19700,0.04200),V(26.19000,-3.59700,0.04200),V(25.79000,-3.59700,0.04200),V(25.79000,-3.54700,0.04200),V(25.37000,-3.54700,0.04200),V(25.37000,-3.60000,0.04200)])]).extrude(V(0,0,0.01200)))
_s.append(Part.Face([_poly([V(36.24500,-14.45000,0.04200),V(36.24500,-14.30000,0.04200),V(36.39500,-14.30000,0.04200),V(36.54500,-14.30000,0.04200),V(36.54500,-14.45000,0.04200),V(36.54500,-14.60000,0.04200),V(36.54500,-19.37200,0.04200),V(36.29300,-19.37200,0.04200),V(36.29300,-19.42200,0.04200),V(35.89300,-19.42200,0.04200),V(35.89300,-19.02200,0.04200),V(36.24500,-19.02200,0.04200),V(36.24500,-14.60000,0.04200),V(36.24500,-14.45000,0.04200)])]).extrude(V(0,0,0.01200)))
_s.append(Part.Face([_poly([V(37.09500,-14.45000,0.04200),V(37.09500,-14.30000,0.04200),V(37.24500,-14.30000,0.04200),V(37.39500,-14.30000,0.04200),V(37.39500,-14.45000,0.04200),V(37.39500,-14.60000,0.04200),V(37.39500,-19.02200,0.04200),V(37.44500,-19.02200,0.04200),V(37.44500,-19.42200,0.04200),V(37.04500,-19.42200,0.04200),V(37.04500,-19.02200,0.04200),V(37.09500,-19.02200,0.04200),V(37.09500,-14.60000,0.04200),V(37.09500,-14.45000,0.04200)])]).extrude(V(0,0,0.01200)))
_s.append(Part.Face([_poly([V(34.84500,-19.33800,0.04200),V(33.72600,-19.33800,0.04200),V(33.72600,-19.38800,0.04200),V(33.32600,-19.38800,0.04200),V(33.32600,-18.98800,0.04200),V(33.72600,-18.98800,0.04200),V(33.72600,-19.03800,0.04200),V(34.54500,-19.03800,0.04200),V(34.54500,-14.60000,0.04200),V(34.54500,-14.45000,0.04200),V(34.54500,-14.30000,0.04200),V(34.69500,-14.30000,0.04200),V(34.84500,-14.30000,0.04200),V(34.84500,-14.45000,0.04200),V(34.84500,-14.60000,0.04200),V(34.84500,-19.33800,0.04200)])]).extrude(V(0,0,0.01200)))
_s.append(Part.Face([_poly([V(31.11800,-16.00800,0.04200),V(31.11800,-15.60800,0.04200),V(31.16800,-15.60800,0.04200),V(31.16800,-11.72500,0.04200),V(31.97000,-11.72500,0.04200),V(32.12000,-11.72500,0.04200),V(32.27000,-11.72500,0.04200),V(32.27000,-11.87500,0.04200),V(32.27000,-12.02500,0.04200),V(32.12000,-12.02500,0.04200),V(31.97000,-12.02500,0.04200),V(31.46800,-12.02500,0.04200),V(31.46800,-15.60800,0.04200),V(31.51800,-15.60800,0.04200),V(31.51800,-16.00800,0.04200),V(31.11800,-16.00800,0.04200)])]).extrude(V(0,0,0.01200)))
_s.append(Part.Face([_poly([V(33.84500,-14.60000,0.04200),V(33.69500,-14.60000,0.04200),V(32.59500,-14.60000,0.04200),V(32.59500,-12.87500,0.04200),V(32.44400,-12.87500,0.04200),V(32.44400,-12.92500,0.04200),V(32.04400,-12.92500,0.04200),V(32.04400,-12.52500,0.04200),V(32.44400,-12.52500,0.04200),V(32.44400,-12.57500,0.04200),V(32.89500,-12.57500,0.04200),V(32.89500,-14.30000,0.04200),V(33.69500,-14.30000,0.04200),V(33.84500,-14.30000,0.04200),V(33.99500,-14.30000,0.04200),V(33.99500,-14.45000,0.04200),V(33.99500,-14.60000,0.04200),V(33.84500,-14.60000,0.04200)])]).extrude(V(0,0,0.01200)))
_s.append(Part.Face([_poly([V(36.82000,-9.75000,0.04200),V(36.82000,-13.15000,0.04200),V(33.42000,-13.15000,0.04200),V(33.42000,-9.75000,0.04200),V(36.82000,-9.75000,0.04200)])]).extrude(V(0,0,0.01200)))
_s.append(Part.Face([_poly([V(38.12000,-9.17500,0.04200),V(38.27000,-9.17500,0.04200),V(39.05500,-9.17500,0.04200),V(39.05500,-10.05600,0.04200),V(39.10500,-10.05600,0.04200),V(39.10500,-10.45600,0.04200),V(38.70500,-10.45600,0.04200),V(38.70500,-10.05600,0.04200),V(38.75500,-10.05600,0.04200),V(38.75500,-9.47500,0.04200),V(38.27000,-9.47500,0.04200),V(38.12000,-9.47500,0.04200),V(37.97000,-9.47500,0.04200),V(37.97000,-9.32500,0.04200),V(37.97000,-9.17500,0.04200),V(38.12000,-9.17500,0.04200)])]).extrude(V(0,0,0.01200)))
_s.append(Part.Face([_poly([V(34.54500,-8.45000,0.04200),V(34.54500,-8.30000,0.04200),V(34.54500,-4.90900,0.04200),V(35.39700,-4.90900,0.04200),V(35.39700,-4.85900,0.04200),V(35.79700,-4.85900,0.04200),V(35.79700,-5.25900,0.04200),V(35.39700,-5.25900,0.04200),V(35.39700,-5.20900,0.04200),V(34.84500,-5.20900,0.04200),V(34.84500,-8.30000,0.04200),V(34.84500,-8.45000,0.04200),V(34.84500,-8.60000,0.04200),V(34.69500,-8.60000,0.04200),V(34.54500,-8.60000,0.04200),V(34.54500,-8.45000,0.04200)])]).extrude(V(0,0,0.01200)))
_s.append(Part.Face([_poly([V(35.39500,-8.45000,0.04200),V(35.39500,-8.30000,0.04200),V(35.39500,-7.26600,0.04200),V(35.34500,-7.26600,0.04200),V(35.34500,-6.86600,0.04200),V(35.74500,-6.86600,0.04200),V(35.74500,-7.26600,0.04200),V(35.69500,-7.26600,0.04200),V(35.69500,-8.30000,0.04200),V(35.69500,-8.45000,0.04200),V(35.69500,-8.60000,0.04200),V(35.54500,-8.60000,0.04200),V(35.39500,-8.60000,0.04200),V(35.39500,-8.45000,0.04200)])]).extrude(V(0,0,0.01200)))
_s.append(Part.Face([_poly([V(36.19500,-3.17800,0.04200),V(36.59500,-3.17800,0.04200),V(36.59500,-3.57800,0.04200),V(36.54500,-3.57800,0.04200),V(36.54500,-8.30000,0.04200),V(36.54500,-8.45000,0.04200),V(36.54500,-8.60000,0.04200),V(36.39500,-8.60000,0.04200),V(36.24500,-8.60000,0.04200),V(36.24500,-8.45000,0.04200),V(36.24500,-8.30000,0.04200),V(36.24500,-3.57800,0.04200),V(36.19500,-3.57800,0.04200),V(36.19500,-3.17800,0.04200)])]).extrude(V(0,0,0.01200)))
_s.append(Part.Face([_poly([V(37.24500,-8.30000,0.04200),V(37.39500,-8.30000,0.04200),V(39.19800,-8.30000,0.04200),V(39.19800,-3.60900,0.04200),V(39.14800,-3.60900,0.04200),V(39.14800,-3.20900,0.04200),V(39.19800,-3.20900,0.04200),V(39.19800,-2.91700,0.04200),V(45.25700,-2.91700,0.04200),V(45.25700,-9.92500,0.04200),V(46.47000,-9.92500,0.04200),V(46.62000,-9.92500,0.04200),V(46.77000,-9.92500,0.04200),V(46.77000,-10.07500,0.04200),V(46.77000,-10.22500,0.04200),V(46.62000,-10.22500,0.04200),V(46.47000,-10.22500,0.04200),V(44.95700,-10.22500,0.04200),V(44.95700,-3.21700,0.04200),V(39.54800,-3.21700,0.04200),V(39.54800,-3.60900,0.04200),V(39.49800,-3.60900,0.04200),V(39.49800,-8.60000,0.04200),V(37.39500,-8.60000,0.04200),V(37.24500,-8.60000,0.04200),V(37.09500,-8.60000,0.04200),V(37.09500,-8.45000,0.04200),V(37.09500,-8.30000,0.04200),V(37.24500,-8.30000,0.04200)])]).extrude(V(0,0,0.01200)))
_s.append(Part.Face([_poly([V(25.97000,-6.75000,0.04200),V(25.97000,-6.60000,0.04200),V(26.12000,-6.60000,0.04200),V(26.27000,-6.60000,0.04200),V(29.64100,-6.60000,0.04200),V(29.64100,-3.58400,0.04200),V(29.59100,-3.58400,0.04200),V(29.59100,-3.18400,0.04200),V(29.99100,-3.18400,0.04200),V(29.99100,-3.58400,0.04200),V(29.94100,-3.58400,0.04200),V(29.94100,-6.90000,0.04200),V(26.27000,-6.90000,0.04200),V(26.12000,-6.90000,0.04200),V(25.97000,-6.90000,0.04200),V(25.97000,-6.75000,0.04200)])]).extrude(V(0,0,0.01200)))
_s.append(Part.Face([_poly([V(26.27000,-6.00000,0.04200),V(26.22000,-6.00000,0.04200),V(26.12000,-6.00000,0.04200),V(25.97000,-6.00000,0.04200),V(25.97000,-5.85000,0.04200),V(25.97000,-5.70000,0.04200),V(25.97000,-5.65000,0.04200),V(26.22000,-5.65000,0.04200),V(26.22000,-5.60000,0.04200),V(26.62000,-5.60000,0.04200),V(26.62000,-6.00000,0.04200),V(26.27000,-6.00000,0.04200)])]).extrude(V(0,0,0.01200)))
_s.append(Part.Face([_poly([V(38.27000,-12.87500,0.04200),V(38.12000,-12.87500,0.04200),V(37.97000,-12.87500,0.04200),V(37.97000,-12.72500,0.04200),V(37.97000,-12.57500,0.04200),V(38.12000,-12.57500,0.04200),V(38.27000,-12.57500,0.04200),V(42.00300,-12.57500,0.04200),V(43.14900,-12.57500,0.04200),V(43.14900,-8.89100,0.04200),V(43.09900,-8.89100,0.04200),V(43.09900,-8.49100,0.04200),V(43.49900,-8.49100,0.04200),V(43.49900,-8.89100,0.04200),V(43.44900,-8.89100,0.04200),V(43.44900,-12.87500,0.04200),V(42.15300,-12.87500,0.04200),V(42.15300,-19.00700,0.04200),V(42.20300,-19.00700,0.04200),V(42.20300,-19.40700,0.04200),V(41.80300,-19.40700,0.04200),V(41.80300,-19.00700,0.04200),V(41.85300,-19.00700,0.04200),V(41.85300,-12.87500,0.04200),V(38.27000,-12.87500,0.04200)])]).extrude(V(0,0,0.01200)))
_s.append(Part.Face([_poly([V(47.34500,-15.35000,0.04200),V(47.34500,-15.20000,0.04200),V(47.34500,-15.05000,0.04200),V(47.49500,-15.05000,0.04200),V(47.64500,-15.05000,0.04200),V(47.74500,-15.05000,0.04200),V(47.74500,-19.35600,0.04200),V(47.69500,-19.35600,0.04200),V(47.69500,-19.40600,0.04200),V(47.29500,-19.40600,0.04200),V(47.29500,-19.00600,0.04200),V(47.44500,-19.00600,0.04200),V(47.44500,-15.35000,0.04200),V(47.34500,-15.35000,0.04200)])]).extrude(V(0,0,0.01200)))
_s.append(Part.Face([_poly([V(39.23000,-19.39000,0.04200),V(39.23000,-18.99000,0.04200),V(39.28000,-18.99000,0.04200),V(39.28000,-16.36600,0.04200),V(39.23000,-16.36600,0.04200),V(39.23000,-15.96600,0.04200),V(39.28000,-15.96600,0.04200),V(39.28000,-13.72500,0.04200),V(38.27000,-13.72500,0.04200),V(38.12000,-13.72500,0.04200),V(37.97000,-13.72500,0.04200),V(37.97000,-13.57500,0.04200),V(37.97000,-13.42500,0.04200),V(38.12000,-13.42500,0.04200),V(38.27000,-13.42500,0.04200),V(39.58000,-13.42500,0.04200),V(39.58000,-15.96600,0.04200),V(39.63000,-15.96600,0.04200),V(39.63000,-16.36600,0.04200),V(39.58000,-16.36600,0.04200),V(39.58000,-18.99000,0.04200),V(39.63000,-18.99000,0.04200),V(39.63000,-19.39000,0.04200),V(39.23000,-19.39000,0.04200)])]).extrude(V(0,0,0.01200)))
_s.append(Part.Face([_poly([V(46.47000,-12.47500,0.04200),V(46.62000,-12.47500,0.04200),V(46.77000,-12.47500,0.04200),V(46.77000,-12.62500,0.04200),V(46.77000,-12.77500,0.04200),V(46.62000,-12.77500,0.04200),V(46.47000,-12.77500,0.04200),V(46.27200,-12.77500,0.04200),V(46.27200,-18.87800,0.04200),V(46.32200,-18.87800,0.04200),V(46.32200,-19.27800,0.04200),V(45.92200,-19.27800,0.04200),V(45.92200,-18.87800,0.04200),V(45.97200,-18.87800,0.04200),V(45.97200,-12.47500,0.04200),V(46.47000,-12.47500,0.04200)])]).extrude(V(0,0,0.01200)))
_s.append(Part.Face([_poly([V(46.74588,-13.88374,0.04200),V(46.74946,-13.86946,0.04200),V(46.75442,-13.85560,0.04200),V(46.76071,-13.84229,0.04200),V(46.76828,-13.82966,0.04200),V(46.77705,-13.81784,0.04200),V(46.78693,-13.80693,0.04200),V(46.79784,-13.79705,0.04200),V(46.80966,-13.78828,0.04200),V(46.82229,-13.78071,0.04200),V(46.83560,-13.77442,0.04200),V(46.84946,-13.76946,0.04200),V(46.86374,-13.76588,0.04200),V(46.87830,-13.76372,0.04200),V(46.89300,-13.76300,0.04200),V(47.09500,-13.76300,0.04200),V(47.09500,-9.67500,0.04200),V(51.59500,-9.67500,0.04200),V(51.59500,-9.35000,0.04200),V(51.59500,-9.20000,0.04200),V(51.59500,-9.05000,0.04200),V(51.74500,-9.05000,0.04200),V(51.89500,-9.05000,0.04200),V(51.89500,-9.20000,0.04200),V(51.89500,-9.35000,0.04200),V(51.89500,-9.97500,0.04200),V(47.39500,-9.97500,0.04200),V(47.39500,-14.06300,0.04200),V(47.04300,-14.06300,0.04200),V(47.04300,-16.54800,0.04200),V(47.09300,-16.54800,0.04200),V(47.09300,-16.94800,0.04200),V(46.69300,-16.94800,0.04200),V(46.69300,-16.54800,0.04200),V(46.74300,-16.54800,0.04200),V(46.74300,-13.91300,0.04200),V(46.74372,-13.89830,0.04200),V(46.74588,-13.88374,0.04200)])]).extrude(V(0,0,0.01200)))
_s.append(Part.Face([_poly([V(38.12000,-11.72500,0.04200),V(38.27000,-11.72500,0.04200),V(41.88500,-11.72500,0.04200),V(41.88500,-8.11800,0.04200),V(41.83500,-8.11800,0.04200),V(41.83500,-7.71800,0.04200),V(42.23500,-7.71800,0.04200),V(42.23500,-8.11800,0.04200),V(42.18500,-8.11800,0.04200),V(42.18500,-12.02500,0.04200),V(38.27000,-12.02500,0.04200),V(38.12000,-12.02500,0.04200),V(37.97000,-12.02500,0.04200),V(37.97000,-11.87500,0.04200),V(37.97000,-11.72500,0.04200),V(38.12000,-11.72500,0.04200)])]).extrude(V(0,0,0.01200)))
_s.append(Part.Face([_poly([V(44.14000,-6.03000,0.04200),V(44.14000,-5.63000,0.04200),V(44.54000,-5.63000,0.04200),V(44.54000,-6.03000,0.04200),V(44.49000,-6.03000,0.04200),V(44.49000,-11.62500,0.04200),V(46.47000,-11.62500,0.04200),V(46.62000,-11.62500,0.04200),V(46.77000,-11.62500,0.04200),V(46.77000,-11.77500,0.04200),V(46.77000,-11.92500,0.04200),V(46.62000,-11.92500,0.04200),V(46.47000,-11.92500,0.04200),V(44.19000,-11.92500,0.04200),V(44.19000,-6.03000,0.04200),V(44.14000,-6.03000,0.04200)])]).extrude(V(0,0,0.01200)))
_s.append(Part.Face([_poly([V(37.97000,-10.87500,0.04200),V(38.12000,-10.87500,0.04200),V(38.27000,-10.87500,0.04200),V(40.22800,-10.87500,0.04200),V(40.22800,-4.33600,0.04200),V(40.17800,-4.33600,0.04200),V(40.17800,-3.93600,0.04200),V(40.57800,-3.93600,0.04200),V(40.57800,-4.33600,0.04200),V(40.52800,-4.33600,0.04200),V(40.52800,-11.17500,0.04200),V(38.27000,-11.17500,0.04200),V(38.12000,-11.17500,0.04200),V(37.97000,-11.17500,0.04200),V(37.97000,-11.02500,0.04200),V(37.97000,-10.87500,0.04200)])]).extrude(V(0,0,0.01200)))
_s.append(Part.Face([_poly([V(45.61800,-10.66700,0.04200),V(46.01800,-10.66700,0.04200),V(46.01800,-10.77500,0.04200),V(46.47000,-10.77500,0.04200),V(46.62000,-10.77500,0.04200),V(46.77000,-10.77500,0.04200),V(46.77000,-10.92500,0.04200),V(46.77000,-11.07500,0.04200),V(46.62000,-11.07500,0.04200),V(46.47000,-11.07500,0.04200),V(45.66800,-11.07500,0.04200),V(45.66800,-11.06700,0.04200),V(45.61800,-11.06700,0.04200),V(45.61800,-10.66700,0.04200)])]).extrude(V(0,0,0.01200)))
_s.append(Part.Face([_poly([V(47.64500,-9.35000,0.04200),V(47.49500,-9.35000,0.04200),V(47.34500,-9.35000,0.04200),V(46.10900,-9.35000,0.04200),V(46.10900,-3.56800,0.04200),V(46.05900,-3.56800,0.04200),V(46.05900,-3.16800,0.04200),V(46.45900,-3.16800,0.04200),V(46.45900,-3.56800,0.04200),V(46.40900,-3.56800,0.04200),V(46.40900,-9.05000,0.04200),V(47.34500,-9.05000,0.04200),V(47.49500,-9.05000,0.04200),V(47.64500,-9.05000,0.04200),V(47.64500,-9.20000,0.04200),V(47.64500,-9.35000,0.04200)])]).extrude(V(0,0,0.01200)))
_s.append(Part.Face([_poly([V(48.09700,-3.60200,0.04200),V(48.04700,-3.60200,0.04200),V(48.04700,-3.20200,0.04200),V(48.44700,-3.20200,0.04200),V(48.44700,-3.60200,0.04200),V(48.39700,-3.60200,0.04200),V(48.39700,-9.05000,0.04200),V(49.04500,-9.05000,0.04200),V(49.19500,-9.05000,0.04200),V(49.34500,-9.05000,0.04200),V(49.34500,-9.20000,0.04200),V(49.34500,-9.35000,0.04200),V(49.19500,-9.35000,0.04200),V(49.04500,-9.35000,0.04200),V(48.09700,-9.35000,0.04200),V(48.09700,-3.60200,0.04200)])]).extrude(V(0,0,0.01200)))
_s.append(Part.Face([_poly([V(51.59500,-15.20000,0.04200),V(51.59500,-15.05000,0.04200),V(51.74500,-15.05000,0.04200),V(51.89500,-15.05000,0.04200),V(51.89500,-15.20000,0.04200),V(51.89500,-15.35000,0.04200),V(51.89500,-19.50000,0.04200),V(51.94500,-19.50000,0.04200),V(51.94500,-19.90000,0.04200),V(51.54500,-19.90000,0.04200),V(51.54500,-19.50000,0.04200),V(51.59500,-19.50000,0.04200),V(51.59500,-15.35000,0.04200),V(51.59500,-15.20000,0.04200)])]).extrude(V(0,0,0.01200)))
_s.append(Part.Face([_poly([V(51.67000,-14.37500,0.04200),V(51.67000,-10.77500,0.04200),V(52.47000,-10.77500,0.04200),V(52.62000,-10.77500,0.04200),V(52.77000,-10.77500,0.04200),V(52.77000,-10.92500,0.04200),V(52.77000,-11.07500,0.04200),V(52.62000,-11.07500,0.04200),V(52.47000,-11.07500,0.04200),V(51.97000,-11.07500,0.04200),V(51.97000,-14.67500,0.04200),V(49.47000,-14.67500,0.04200),V(49.47000,-19.42500,0.04200),V(49.52000,-19.42500,0.04200),V(49.52000,-19.82500,0.04200),V(49.12000,-19.82500,0.04200),V(49.12000,-19.42500,0.04200),V(49.17000,-19.42500,0.04200),V(49.17000,-14.37500,0.04200),V(51.67000,-14.37500,0.04200)])]).extrude(V(0,0,0.01200)))
_s.append(Part.Face([_poly([V(52.47000,-12.62500,0.04200),V(52.47000,-12.47500,0.04200),V(52.62000,-12.47500,0.04200),V(52.77000,-12.47500,0.04200),V(55.72200,-12.47500,0.04200),V(55.72200,-19.05000,0.04200),V(55.77200,-19.05000,0.04200),V(55.77200,-19.45000,0.04200),V(55.37200,-19.45000,0.04200),V(55.37200,-19.05000,0.04200),V(55.42200,-19.05000,0.04200),V(55.42200,-12.77500,0.04200),V(52.77000,-12.77500,0.04200),V(52.62000,-12.77500,0.04200),V(52.47000,-12.77500,0.04200),V(52.47000,-12.62500,0.04200)])]).extrude(V(0,0,0.01200)))
_s.append(Part.Face([_poly([V(52.47000,-13.65000,0.04200),V(52.47000,-13.62500,0.04200),V(52.47000,-13.47500,0.04200),V(52.47000,-13.32500,0.04200),V(52.62000,-13.32500,0.04200),V(52.77000,-13.32500,0.04200),V(52.77000,-13.35000,0.04200),V(54.52000,-13.35000,0.04200),V(54.52000,-18.90000,0.04200),V(54.57000,-18.90000,0.04200),V(54.57000,-19.30000,0.04200),V(54.17000,-19.30000,0.04200),V(54.17000,-18.90000,0.04200),V(54.22000,-18.90000,0.04200),V(54.22000,-13.65000,0.04200),V(52.47000,-13.65000,0.04200)])]).extrude(V(0,0,0.01200)))
_s.append(Part.Face([_poly([V(49.89500,-15.20000,0.04200),V(49.89500,-15.05000,0.04200),V(50.04500,-15.05000,0.04200),V(50.19500,-15.05000,0.04200),V(50.19500,-15.20000,0.04200),V(50.19500,-15.35000,0.04200),V(50.19500,-15.78100,0.04200),V(50.24500,-15.78100,0.04200),V(50.24500,-16.18100,0.04200),V(49.84500,-16.18100,0.04200),V(49.84500,-15.78100,0.04200),V(49.89500,-15.78100,0.04200),V(49.89500,-15.35000,0.04200),V(49.89500,-15.20000,0.04200)])]).extrude(V(0,0,0.01200)))
_s.append(Part.Face([_poly([V(47.92000,-10.50000,0.04200),V(51.32000,-10.50000,0.04200),V(51.32000,-13.90000,0.04200),V(47.92000,-13.90000,0.04200),V(47.92000,-10.50000,0.04200)])]).extrude(V(0,0,0.01200)))
_s.append(Part.Face([_poly([V(53.82000,-10.40000,0.04200),V(53.82000,-10.00000,0.04200),V(53.97000,-10.00000,0.04200),V(53.97000,-5.25000,0.04200),V(59.87000,-5.25000,0.04200),V(59.87000,-4.85000,0.04200),V(59.87000,-4.70000,0.04200),V(59.87000,-4.55000,0.04200),V(59.87000,-3.58100,0.04200),V(59.82000,-3.58100,0.04200),V(59.82000,-3.18100,0.04200),V(60.22000,-3.18100,0.04200),V(60.22000,-3.58100,0.04200),V(60.17000,-3.58100,0.04200),V(60.17000,-4.55000,0.04200),V(60.17000,-4.70000,0.04200),V(60.17000,-4.85000,0.04200),V(60.17000,-5.55000,0.04200),V(54.27000,-5.55000,0.04200),V(54.27000,-10.35000,0.04200),V(54.22000,-10.35000,0.04200),V(54.22000,-10.40000,0.04200),V(53.82000,-10.40000,0.04200)])]).extrude(V(0,0,0.01200)))
_s.append(Part.Face([_poly([V(52.47000,-10.22500,0.04200),V(52.47000,-10.07500,0.04200),V(52.47000,-9.92500,0.04200),V(52.48700,-9.92500,0.04200),V(52.48700,-4.49200,0.04200),V(52.43700,-4.49200,0.04200),V(52.43700,-4.09200,0.04200),V(52.83700,-4.09200,0.04200),V(52.83700,-4.49200,0.04200),V(52.78700,-4.49200,0.04200),V(52.78700,-10.22500,0.04200),V(52.77000,-10.22500,0.04200),V(52.62000,-10.22500,0.04200),V(52.47000,-10.22500,0.04200)])]).extrude(V(0,0,0.01200)))
_s.append(Part.Face([_poly([V(53.22600,-9.57000,0.04200),V(53.22600,-9.17000,0.04200),V(53.27600,-9.17000,0.04200),V(53.27600,-4.27800,0.04200),V(56.09000,-4.27800,0.04200),V(56.09000,-3.48200,0.04200),V(56.04000,-3.48200,0.04200),V(56.04000,-3.08200,0.04200),V(56.44000,-3.08200,0.04200),V(56.44000,-3.48200,0.04200),V(56.39000,-3.48200,0.04200),V(56.39000,-4.42800,0.04200),V(56.39000,-4.55000,0.04200),V(58.07000,-4.55000,0.04200),V(58.22000,-4.55000,0.04200),V(58.37000,-4.55000,0.04200),V(58.37000,-4.70000,0.04200),V(58.37000,-4.85000,0.04200),V(58.22000,-4.85000,0.04200),V(58.07000,-4.85000,0.04200),V(56.09000,-4.85000,0.04200),V(56.09000,-4.57800,0.04200),V(53.57600,-4.57800,0.04200),V(53.57600,-9.17000,0.04200),V(53.62600,-9.17000,0.04200),V(53.62600,-9.57000,0.04200),V(53.22600,-9.57000,0.04200)])]).extrude(V(0,0,0.01200)))
_s.append(Part.Face([_poly([V(50.93000,-8.62100,0.04200),V(50.88000,-8.62100,0.04200),V(50.88000,-9.05000,0.04200),V(50.89500,-9.05000,0.04200),V(51.04500,-9.05000,0.04200),V(51.04500,-9.20000,0.04200),V(51.04500,-9.35000,0.04200),V(50.89500,-9.35000,0.04200),V(50.74500,-9.35000,0.04200),V(50.58000,-9.35000,0.04200),V(50.58000,-8.62100,0.04200),V(50.53000,-8.62100,0.04200),V(50.53000,-8.22100,0.04200),V(50.93000,-8.22100,0.04200),V(50.93000,-8.62100,0.04200)])]).extrude(V(0,0,0.01200)))
_s.append(Part.Face([_poly([V(49.19200,-6.82800,0.04200),V(49.19200,-7.63100,0.04200),V(49.24200,-7.63100,0.04200),V(49.24200,-8.03100,0.04200),V(48.84200,-8.03100,0.04200),V(48.84200,-7.63100,0.04200),V(48.89200,-7.63100,0.04200),V(48.89200,-6.52800,0.04200),V(49.64700,-6.52800,0.04200),V(49.64700,-3.61000,0.04200),V(49.59700,-3.61000,0.04200),V(49.59700,-3.21000,0.04200),V(49.99700,-3.21000,0.04200),V(49.99700,-3.61000,0.04200),V(49.94700,-3.61000,0.04200),V(49.94700,-6.67800,0.04200),V(49.94700,-8.35000,0.04200),V(49.94700,-9.05000,0.04200),V(50.04500,-9.05000,0.04200),V(50.19500,-9.05000,0.04200),V(50.19500,-9.20000,0.04200),V(50.19500,-9.35000,0.04200),V(50.04500,-9.35000,0.04200),V(49.89500,-9.35000,0.04200),V(49.64700,-9.35000,0.04200),V(49.64700,-8.35000,0.04200),V(49.64700,-6.82800,0.04200),V(49.19200,-6.82800,0.04200)])]).extrude(V(0,0,0.01200)))
_s.append(Part.Face([_poly([V(57.47000,-5.90000,0.04200),V(57.47000,-6.05000,0.04200),V(57.47000,-6.20000,0.04200),V(57.32000,-6.20000,0.04200),V(57.17000,-6.20000,0.04200),V(56.71900,-6.20000,0.04200),V(56.71900,-6.31100,0.04200),V(56.31900,-6.31100,0.04200),V(56.31900,-5.91100,0.04200),V(56.36900,-5.91100,0.04200),V(56.36900,-5.90000,0.04200),V(57.17000,-5.90000,0.04200),V(57.32000,-5.90000,0.04200),V(57.47000,-5.90000,0.04200)])]).extrude(V(0,0,0.01200)))
_s.append(Part.Face([_poly([V(51.52600,-3.58800,0.04200),V(51.52600,-3.18800,0.04200),V(51.92600,-3.18800,0.04200),V(51.92600,-3.58800,0.04200),V(51.87600,-3.58800,0.04200),V(51.87600,-5.80900,0.04200),V(51.92600,-5.80900,0.04200),V(51.92600,-6.20900,0.04200),V(51.52600,-6.20900,0.04200),V(51.52600,-5.80900,0.04200),V(51.57600,-5.80900,0.04200),V(51.57600,-3.58800,0.04200),V(51.52600,-3.58800,0.04200)])]).extrude(V(0,0,0.01200)))
_s.append(Part.Face([_poly([V(57.17000,-6.80000,0.04200),V(57.32000,-6.80000,0.04200),V(57.47000,-6.80000,0.04200),V(57.47000,-6.95000,0.04200),V(57.47000,-7.10000,0.04200),V(57.32000,-7.10000,0.04200),V(57.32000,-17.93200,0.04200),V(57.37000,-17.93200,0.04200),V(57.37000,-18.33200,0.04200),V(56.97000,-18.33200,0.04200),V(56.97000,-17.93200,0.04200),V(57.02000,-17.93200,0.04200),V(57.02000,-6.80000,0.04200),V(57.17000,-6.80000,0.04200)])]).extrude(V(0,0,0.01200)))
_s.append(Part.Face([_poly([V(59.65000,-17.70000,0.04200),V(61.32000,-17.70000,0.04200),V(61.47000,-17.70000,0.04200),V(61.62000,-17.70000,0.04200),V(61.62000,-17.85000,0.04200),V(61.62000,-18.00000,0.04200),V(61.47000,-18.00000,0.04200),V(61.32000,-18.00000,0.04200),V(59.65000,-18.00000,0.04200),V(59.62000,-18.00000,0.04200),V(59.47000,-18.00000,0.04200),V(59.32000,-18.00000,0.04200),V(59.25000,-18.00000,0.04200),V(59.25000,-17.60000,0.04200),V(59.65000,-17.60000,0.04200),V(59.65000,-17.70000,0.04200)])]).extrude(V(0,0,0.01200)))
_s.append(Part.Face([_poly([V(58.68600,-14.04386,0.04200),V(58.68342,-14.03840,0.04200),V(58.67846,-14.02454,0.04200),V(58.67488,-14.01026,0.04200),V(58.67272,-13.99570,0.04200),V(58.67200,-13.98100,0.04200),V(58.67200,-13.82500,0.04200),V(59.92200,-13.82500,0.04200),V(59.92200,-13.37000,0.04200),V(61.22000,-13.37000,0.04200),V(62.57200,-13.37000,0.04200),V(62.57200,-6.20000,0.04200),V(61.97000,-6.20000,0.04200),V(61.82000,-6.20000,0.04200),V(61.67000,-6.20000,0.04200),V(61.67000,-6.05000,0.04200),V(61.67000,-5.90000,0.04200),V(61.82000,-5.90000,0.04200),V(61.97000,-5.90000,0.04200),V(62.87200,-5.90000,0.04200),V(62.87200,-13.67000,0.04200),V(61.22000,-13.67000,0.04200),V(60.22200,-13.67000,0.04200),V(60.22200,-13.97500,0.04200),V(60.22128,-13.98970,0.04200),V(60.21912,-14.00426,0.04200),V(60.21554,-14.01854,0.04200),V(60.21058,-14.03240,0.04200),V(60.20429,-14.04571,0.04200),V(60.19672,-14.05834,0.04200),V(60.18795,-14.07016,0.04200),V(60.17807,-14.08107,0.04200),V(60.16716,-14.09095,0.04200),V(60.15534,-14.09972,0.04200),V(60.14271,-14.10729,0.04200),V(60.12940,-14.11358,0.04200),V(60.11554,-14.11854,0.04200),V(60.10126,-14.12212,0.04200),V(60.08670,-14.12428,0.04200),V(60.07200,-14.12500,0.04200),V(58.98600,-14.12500,0.04200),V(58.98600,-15.75000,0.04200),V(58.82200,-15.75000,0.04200),V(58.37000,-15.75000,0.04200),V(58.22000,-15.75000,0.04200),V(58.07000,-15.75000,0.04200),V(58.07000,-15.60000,0.04200),V(58.07000,-15.45000,0.04200),V(58.22000,-15.45000,0.04200),V(58.37000,-15.45000,0.04200),V(58.68600,-15.45000,0.04200),V(58.68600,-14.04386,0.04200)])]).extrude(V(0,0,0.01200)))
_s.append(Part.Face([_poly([V(59.52000,-16.55000,0.04200),V(59.52000,-14.65000,0.04200),V(61.42000,-14.65000,0.04200),V(61.42000,-16.55000,0.04200),V(59.52000,-16.55000,0.04200)])]).extrude(V(0,0,0.01200)))
_s.append(Part.Face([_poly([V(62.57000,-15.25000,0.04200),V(62.57000,-14.95000,0.04200),V(62.87000,-14.95000,0.04200),V(62.87000,-15.25000,0.04200),V(62.57000,-15.25000,0.04200)])]).extrude(V(0,0,0.01200)))
_s.append(Part.Face([_poly([V(58.37000,-14.75000,0.04200),V(58.22000,-14.75000,0.04200),V(58.07000,-14.75000,0.04200),V(58.05500,-14.75000,0.04200),V(58.05500,-12.29000,0.04200),V(60.77000,-12.29000,0.04200),V(60.77000,-9.35000,0.04200),V(60.77000,-9.20000,0.04200),V(60.77000,-9.05000,0.04200),V(60.92000,-9.05000,0.04200),V(61.07000,-9.05000,0.04200),V(61.07000,-9.20000,0.04200),V(61.07000,-9.35000,0.04200),V(61.07000,-12.59000,0.04200),V(58.35500,-12.59000,0.04200),V(58.35500,-14.45000,0.04200),V(58.37000,-14.45000,0.04200),V(58.37000,-14.60000,0.04200),V(58.37000,-14.75000,0.04200)])]).extrude(V(0,0,0.01200)))
_s.append(Part.Face([_poly([V(59.32000,-13.50000,0.04200),V(59.32000,-13.20000,0.04200),V(59.62000,-13.20000,0.04200),V(59.62000,-13.50000,0.04200),V(59.32000,-13.50000,0.04200)])]).extrude(V(0,0,0.01200)))
_s.append(Part.Face([_poly([V(61.68400,-8.00000,0.04200),V(61.67000,-8.00000,0.04200),V(61.67000,-7.85000,0.04200),V(61.67000,-7.70000,0.04200),V(61.82000,-7.70000,0.04200),V(61.97000,-7.70000,0.04200),V(61.98400,-7.70000,0.04200),V(61.98400,-11.10200,0.04200),V(61.98400,-11.25200,0.04200),V(61.98400,-11.40200,0.04200),V(61.83400,-11.40200,0.04200),V(61.68400,-11.40200,0.04200),V(61.68400,-11.25200,0.04200),V(61.68400,-11.10200,0.04200),V(61.68400,-8.00000,0.04200)])]).extrude(V(0,0,0.01200)))
_s.append(Part.Face([_poly([V(59.87000,-9.20000,0.04200),V(59.87000,-9.05000,0.04200),V(60.02000,-9.05000,0.04200),V(60.17000,-9.05000,0.04200),V(60.17000,-9.20000,0.04200),V(60.17000,-9.35000,0.04200),V(60.17000,-10.04300,0.04200),V(60.22000,-10.04300,0.04200),V(60.22000,-10.44300,0.04200),V(59.82000,-10.44300,0.04200),V(59.82000,-10.04300,0.04200),V(59.87000,-10.04300,0.04200),V(59.87000,-9.35000,0.04200),V(59.87000,-9.20000,0.04200)])]).extrude(V(0,0,0.01200)))
_s.append(Part.Face([_poly([V(58.79500,-8.93400,0.04200),V(58.79500,-8.88400,0.04200),V(59.19500,-8.88400,0.04200),V(59.19500,-9.28400,0.04200),V(58.79500,-9.28400,0.04200),V(58.79500,-9.23400,0.04200),V(58.37000,-9.23400,0.04200),V(58.37000,-9.35000,0.04200),V(58.22000,-9.35000,0.04200),V(58.07000,-9.35000,0.04200),V(58.07000,-9.20000,0.04200),V(58.07000,-9.05000,0.04200),V(58.07000,-8.93400,0.04200),V(58.79500,-8.93400,0.04200)])]).extrude(V(0,0,0.01200)))
_s.append(Part.Face([_poly([V(58.62000,-7.90000,0.04200),V(58.62000,-6.00000,0.04200),V(60.52000,-6.00000,0.04200),V(60.52000,-7.90000,0.04200),V(58.62000,-7.90000,0.04200)])]).extrude(V(0,0,0.01200)))
_s.append(Part.Face([_poly([V(62.99200,-3.18100,0.04200),V(63.39200,-3.18100,0.04200),V(63.39200,-3.58100,0.04200),V(63.34200,-3.58100,0.04200),V(63.34200,-4.85000,0.04200),V(61.07000,-4.85000,0.04200),V(60.92000,-4.85000,0.04200),V(60.77000,-4.85000,0.04200),V(60.77000,-4.70000,0.04200),V(60.77000,-4.55000,0.04200),V(60.92000,-4.55000,0.04200),V(61.07000,-4.55000,0.04200),V(63.04200,-4.55000,0.04200),V(63.04200,-3.58100,0.04200),V(62.99200,-3.58100,0.04200),V(62.99200,-3.18100,0.04200)])]).extrude(V(0,0,0.01200)))
_add('2nd Routing Conductor' + '_L5', _fuse(_s), (0.5686,0.1176,0.7059), surface=True)
# --- layer 49 (L49) : z 0.0540..0.0640 mm ---
_s = []
_s.append(Part.Face([_poly([V(17.01400,-23.39500,-0.63500),V(16.87600,-23.46900,-0.63500),V(16.72600,-23.51500,-0.63500),V(16.57000,-23.53000,-0.63500),V(16.41400,-23.51500,-0.63500),V(16.26400,-23.46900,-0.63500),V(16.12600,-23.39500,-0.63500),V(16.00400,-23.29600,-0.63500),V(15.90500,-23.17400,-0.63500),V(15.83100,-23.03600,-0.63500),V(15.78500,-22.88600,-0.63500),V(15.77000,-22.73000,-0.63500),V(15.78500,-22.57400,-0.63500),V(15.83100,-22.42400,-0.63500),V(15.90500,-22.28600,-0.63500),V(16.00400,-22.16400,-0.63500),V(16.12600,-22.06500,-0.63500),V(16.26400,-21.99100,-0.63500),V(16.41400,-21.94500,-0.63500),V(16.57000,-21.93000,-0.63500),V(16.72600,-21.94500,-0.63500),V(16.87600,-21.99100,-0.63500),V(17.01400,-22.06500,-0.63500),V(17.13600,-22.16400,-0.63500),V(17.23500,-22.28600,-0.63500),V(17.30900,-22.42400,-0.63500),V(17.35500,-22.57400,-0.63500),V(17.37000,-22.73000,-0.63500),V(17.35500,-22.88600,-0.63500),V(17.30900,-23.03600,-0.63500),V(17.23500,-23.17400,-0.63500),V(17.13600,-23.29600,-0.63500),V(17.01400,-23.39500,-0.63500)])]).extrude(V(0,0,0.69900)))
_s.append(Part.Face([_poly([V(19.55400,-23.39500,-0.63500),V(19.41600,-23.46900,-0.63500),V(19.26600,-23.51500,-0.63500),V(19.11000,-23.53000,-0.63500),V(18.95400,-23.51500,-0.63500),V(18.80400,-23.46900,-0.63500),V(18.66600,-23.39500,-0.63500),V(18.54400,-23.29600,-0.63500),V(18.44500,-23.17400,-0.63500),V(18.37100,-23.03600,-0.63500),V(18.32500,-22.88600,-0.63500),V(18.31000,-22.73000,-0.63500),V(18.32500,-22.57400,-0.63500),V(18.37100,-22.42400,-0.63500),V(18.44500,-22.28600,-0.63500),V(18.54400,-22.16400,-0.63500),V(18.66600,-22.06500,-0.63500),V(18.80400,-21.99100,-0.63500),V(18.95400,-21.94500,-0.63500),V(19.11000,-21.93000,-0.63500),V(19.26600,-21.94500,-0.63500),V(19.41600,-21.99100,-0.63500),V(19.55400,-22.06500,-0.63500),V(19.67600,-22.16400,-0.63500),V(19.77500,-22.28600,-0.63500),V(19.84900,-22.42400,-0.63500),V(19.89500,-22.57400,-0.63500),V(19.91000,-22.73000,-0.63500),V(19.89500,-22.88600,-0.63500),V(19.84900,-23.03600,-0.63500),V(19.77500,-23.17400,-0.63500),V(19.67600,-23.29600,-0.63500),V(19.55400,-23.39500,-0.63500)])]).extrude(V(0,0,0.69900)))
_s.append(Part.Face([_poly([V(22.09400,-23.39500,-0.63500),V(21.95600,-23.46900,-0.63500),V(21.80600,-23.51500,-0.63500),V(21.65000,-23.53000,-0.63500),V(21.49400,-23.51500,-0.63500),V(21.34400,-23.46900,-0.63500),V(21.20600,-23.39500,-0.63500),V(21.08400,-23.29600,-0.63500),V(20.98500,-23.17400,-0.63500),V(20.91100,-23.03600,-0.63500),V(20.86500,-22.88600,-0.63500),V(20.85000,-22.73000,-0.63500),V(20.86500,-22.57400,-0.63500),V(20.91100,-22.42400,-0.63500),V(20.98500,-22.28600,-0.63500),V(21.08400,-22.16400,-0.63500),V(21.20600,-22.06500,-0.63500),V(21.34400,-21.99100,-0.63500),V(21.49400,-21.94500,-0.63500),V(21.65000,-21.93000,-0.63500),V(21.80600,-21.94500,-0.63500),V(21.95600,-21.99100,-0.63500),V(22.09400,-22.06500,-0.63500),V(22.21600,-22.16400,-0.63500),V(22.31500,-22.28600,-0.63500),V(22.38900,-22.42400,-0.63500),V(22.43500,-22.57400,-0.63500),V(22.45000,-22.73000,-0.63500),V(22.43500,-22.88600,-0.63500),V(22.38900,-23.03600,-0.63500),V(22.31500,-23.17400,-0.63500),V(22.21600,-23.29600,-0.63500),V(22.09400,-23.39500,-0.63500)])]).extrude(V(0,0,0.69900)))
_s.append(Part.Face([_poly([V(24.49600,-23.46900,-0.63500),V(24.34600,-23.51500,-0.63500),V(24.19000,-23.53000,-0.63500),V(24.03400,-23.51500,-0.63500),V(23.88400,-23.46900,-0.63500),V(23.74600,-23.39500,-0.63500),V(23.62400,-23.29600,-0.63500),V(23.52500,-23.17400,-0.63500),V(23.45100,-23.03600,-0.63500),V(23.40500,-22.88600,-0.63500),V(23.39000,-22.73000,-0.63500),V(23.40500,-22.57400,-0.63500),V(23.45100,-22.42400,-0.63500),V(23.52500,-22.28600,-0.63500),V(23.62400,-22.16400,-0.63500),V(23.74600,-22.06500,-0.63500),V(23.88400,-21.99100,-0.63500),V(24.03400,-21.94500,-0.63500),V(24.19000,-21.93000,-0.63500),V(24.34600,-21.94500,-0.63500),V(24.49600,-21.99100,-0.63500),V(24.63400,-22.06500,-0.63500),V(24.75600,-22.16400,-0.63500),V(24.85500,-22.28600,-0.63500),V(24.92900,-22.42400,-0.63500),V(24.97500,-22.57400,-0.63500),V(24.99000,-22.73000,-0.63500),V(24.97500,-22.88600,-0.63500),V(24.92900,-23.03600,-0.63500),V(24.85500,-23.17400,-0.63500),V(24.75600,-23.29600,-0.63500),V(24.63400,-23.39500,-0.63500),V(24.49600,-23.46900,-0.63500)])]).extrude(V(0,0,0.69900)))
_s.append(Part.Face([_poly([V(27.03600,-23.46900,-0.63500),V(26.88600,-23.51500,-0.63500),V(26.73000,-23.53000,-0.63500),V(26.57400,-23.51500,-0.63500),V(26.42400,-23.46900,-0.63500),V(26.28600,-23.39500,-0.63500),V(26.16400,-23.29600,-0.63500),V(26.06500,-23.17400,-0.63500),V(25.99100,-23.03600,-0.63500),V(25.94500,-22.88600,-0.63500),V(25.93000,-22.73000,-0.63500),V(25.94500,-22.57400,-0.63500),V(25.99100,-22.42400,-0.63500),V(26.06500,-22.28600,-0.63500),V(26.16400,-22.16400,-0.63500),V(26.28600,-22.06500,-0.63500),V(26.42400,-21.99100,-0.63500),V(26.57400,-21.94500,-0.63500),V(26.73000,-21.93000,-0.63500),V(26.88600,-21.94500,-0.63500),V(27.03600,-21.99100,-0.63500),V(27.17400,-22.06500,-0.63500),V(27.29600,-22.16400,-0.63500),V(27.39500,-22.28600,-0.63500),V(27.46900,-22.42400,-0.63500),V(27.51500,-22.57400,-0.63500),V(27.53000,-22.73000,-0.63500),V(27.51500,-22.88600,-0.63500),V(27.46900,-23.03600,-0.63500),V(27.39500,-23.17400,-0.63500),V(27.29600,-23.29600,-0.63500),V(27.17400,-23.39500,-0.63500),V(27.03600,-23.46900,-0.63500)])]).extrude(V(0,0,0.69900)))
_s.append(Part.Face([_poly([V(29.71400,-23.39500,-0.63500),V(29.57600,-23.46900,-0.63500),V(29.42600,-23.51500,-0.63500),V(29.27000,-23.53000,-0.63500),V(29.11400,-23.51500,-0.63500),V(28.96400,-23.46900,-0.63500),V(28.82600,-23.39500,-0.63500),V(28.70400,-23.29600,-0.63500),V(28.60500,-23.17400,-0.63500),V(28.53100,-23.03600,-0.63500),V(28.48500,-22.88600,-0.63500),V(28.47000,-22.73000,-0.63500),V(28.48500,-22.57400,-0.63500),V(28.53100,-22.42400,-0.63500),V(28.60500,-22.28600,-0.63500),V(28.70400,-22.16400,-0.63500),V(28.82600,-22.06500,-0.63500),V(28.96400,-21.99100,-0.63500),V(29.11400,-21.94500,-0.63500),V(29.27000,-21.93000,-0.63500),V(29.42600,-21.94500,-0.63500),V(29.57600,-21.99100,-0.63500),V(29.71400,-22.06500,-0.63500),V(29.83600,-22.16400,-0.63500),V(29.93500,-22.28600,-0.63500),V(30.00900,-22.42400,-0.63500),V(30.05500,-22.57400,-0.63500),V(30.07000,-22.73000,-0.63500),V(30.05500,-22.88600,-0.63500),V(30.00900,-23.03600,-0.63500),V(29.93500,-23.17400,-0.63500),V(29.83600,-23.29600,-0.63500),V(29.71400,-23.39500,-0.63500)])]).extrude(V(0,0,0.69900)))
_s.append(Part.Face([_poly([V(32.25400,-23.39500,-0.63500),V(32.11600,-23.46900,-0.63500),V(31.96600,-23.51500,-0.63500),V(31.81000,-23.53000,-0.63500),V(31.65400,-23.51500,-0.63500),V(31.50400,-23.46900,-0.63500),V(31.36600,-23.39500,-0.63500),V(31.24400,-23.29600,-0.63500),V(31.14500,-23.17400,-0.63500),V(31.07100,-23.03600,-0.63500),V(31.02500,-22.88600,-0.63500),V(31.01000,-22.73000,-0.63500),V(31.02500,-22.57400,-0.63500),V(31.07100,-22.42400,-0.63500),V(31.14500,-22.28600,-0.63500),V(31.24400,-22.16400,-0.63500),V(31.36600,-22.06500,-0.63500),V(31.50400,-21.99100,-0.63500),V(31.65400,-21.94500,-0.63500),V(31.81000,-21.93000,-0.63500),V(31.96600,-21.94500,-0.63500),V(32.11600,-21.99100,-0.63500),V(32.25400,-22.06500,-0.63500),V(32.37600,-22.16400,-0.63500),V(32.47500,-22.28600,-0.63500),V(32.54900,-22.42400,-0.63500),V(32.59500,-22.57400,-0.63500),V(32.61000,-22.73000,-0.63500),V(32.59500,-22.88600,-0.63500),V(32.54900,-23.03600,-0.63500),V(32.47500,-23.17400,-0.63500),V(32.37600,-23.29600,-0.63500),V(32.25400,-23.39500,-0.63500)])]).extrude(V(0,0,0.69900)))
_s.append(Part.Face([_poly([V(34.79400,-23.39500,-0.63500),V(34.65600,-23.46900,-0.63500),V(34.50600,-23.51500,-0.63500),V(34.35000,-23.53000,-0.63500),V(34.19400,-23.51500,-0.63500),V(34.04400,-23.46900,-0.63500),V(33.90600,-23.39500,-0.63500),V(33.78400,-23.29600,-0.63500),V(33.68500,-23.17400,-0.63500),V(33.61100,-23.03600,-0.63500),V(33.56500,-22.88600,-0.63500),V(33.55000,-22.73000,-0.63500),V(33.56500,-22.57400,-0.63500),V(33.61100,-22.42400,-0.63500),V(33.68500,-22.28600,-0.63500),V(33.78400,-22.16400,-0.63500),V(33.90600,-22.06500,-0.63500),V(34.04400,-21.99100,-0.63500),V(34.19400,-21.94500,-0.63500),V(34.35000,-21.93000,-0.63500),V(34.50600,-21.94500,-0.63500),V(34.65600,-21.99100,-0.63500),V(34.79400,-22.06500,-0.63500),V(34.91600,-22.16400,-0.63500),V(35.01500,-22.28600,-0.63500),V(35.08900,-22.42400,-0.63500),V(35.13500,-22.57400,-0.63500),V(35.15000,-22.73000,-0.63500),V(35.13500,-22.88600,-0.63500),V(35.08900,-23.03600,-0.63500),V(35.01500,-23.17400,-0.63500),V(34.91600,-23.29600,-0.63500),V(34.79400,-23.39500,-0.63500)])]).extrude(V(0,0,0.69900)))
_s.append(Part.Face([_poly([V(37.19600,-23.46900,-0.63500),V(37.04600,-23.51500,-0.63500),V(36.89000,-23.53000,-0.63500),V(36.73400,-23.51500,-0.63500),V(36.58400,-23.46900,-0.63500),V(36.44600,-23.39500,-0.63500),V(36.32400,-23.29600,-0.63500),V(36.22500,-23.17400,-0.63500),V(36.15100,-23.03600,-0.63500),V(36.10500,-22.88600,-0.63500),V(36.09000,-22.73000,-0.63500),V(36.10500,-22.57400,-0.63500),V(36.15100,-22.42400,-0.63500),V(36.22500,-22.28600,-0.63500),V(36.32400,-22.16400,-0.63500),V(36.44600,-22.06500,-0.63500),V(36.58400,-21.99100,-0.63500),V(36.73400,-21.94500,-0.63500),V(36.89000,-21.93000,-0.63500),V(37.04600,-21.94500,-0.63500),V(37.19600,-21.99100,-0.63500),V(37.33400,-22.06500,-0.63500),V(37.45600,-22.16400,-0.63500),V(37.55500,-22.28600,-0.63500),V(37.62900,-22.42400,-0.63500),V(37.67500,-22.57400,-0.63500),V(37.69000,-22.73000,-0.63500),V(37.67500,-22.88600,-0.63500),V(37.62900,-23.03600,-0.63500),V(37.55500,-23.17400,-0.63500),V(37.45600,-23.29600,-0.63500),V(37.33400,-23.39500,-0.63500),V(37.19600,-23.46900,-0.63500)])]).extrude(V(0,0,0.69900)))
_s.append(Part.Face([_poly([V(39.73600,-23.46900,-0.63500),V(39.58600,-23.51500,-0.63500),V(39.43000,-23.53000,-0.63500),V(39.27400,-23.51500,-0.63500),V(39.12400,-23.46900,-0.63500),V(38.98600,-23.39500,-0.63500),V(38.86400,-23.29600,-0.63500),V(38.76500,-23.17400,-0.63500),V(38.69100,-23.03600,-0.63500),V(38.64500,-22.88600,-0.63500),V(38.63000,-22.73000,-0.63500),V(38.64500,-22.57400,-0.63500),V(38.69100,-22.42400,-0.63500),V(38.76500,-22.28600,-0.63500),V(38.86400,-22.16400,-0.63500),V(38.98600,-22.06500,-0.63500),V(39.12400,-21.99100,-0.63500),V(39.27400,-21.94500,-0.63500),V(39.43000,-21.93000,-0.63500),V(39.58600,-21.94500,-0.63500),V(39.73600,-21.99100,-0.63500),V(39.87400,-22.06500,-0.63500),V(39.99600,-22.16400,-0.63500),V(40.09500,-22.28600,-0.63500),V(40.16900,-22.42400,-0.63500),V(40.21500,-22.57400,-0.63500),V(40.23000,-22.73000,-0.63500),V(40.21500,-22.88600,-0.63500),V(40.16900,-23.03600,-0.63500),V(40.09500,-23.17400,-0.63500),V(39.99600,-23.29600,-0.63500),V(39.87400,-23.39500,-0.63500),V(39.73600,-23.46900,-0.63500)])]).extrude(V(0,0,0.69900)))
_s.append(Part.Face([_poly([V(17.01400,-0.53500,-0.63500),V(16.87600,-0.60900,-0.63500),V(16.72600,-0.65500,-0.63500),V(16.57000,-0.67000,-0.63500),V(16.41400,-0.65500,-0.63500),V(16.26400,-0.60900,-0.63500),V(16.12600,-0.53500,-0.63500),V(16.00400,-0.43600,-0.63500),V(15.90500,-0.31400,-0.63500),V(15.83100,-0.17600,-0.63500),V(15.78500,-0.02600,-0.63500),V(15.77000,0.13000,-0.63500),V(15.78500,0.28600,-0.63500),V(15.83100,0.43600,-0.63500),V(15.90500,0.57400,-0.63500),V(16.00400,0.69600,-0.63500),V(16.12600,0.79500,-0.63500),V(16.26400,0.86900,-0.63500),V(16.41400,0.91500,-0.63500),V(16.57000,0.93000,-0.63500),V(16.72600,0.91500,-0.63500),V(16.87600,0.86900,-0.63500),V(17.01400,0.79500,-0.63500),V(17.13600,0.69600,-0.63500),V(17.23500,0.57400,-0.63500),V(17.30900,0.43600,-0.63500),V(17.35500,0.28600,-0.63500),V(17.37000,0.13000,-0.63500),V(17.35500,-0.02600,-0.63500),V(17.30900,-0.17600,-0.63500),V(17.23500,-0.31400,-0.63500),V(17.13600,-0.43600,-0.63500),V(17.01400,-0.53500,-0.63500)])]).extrude(V(0,0,0.69900)))
_s.append(Part.Face([_poly([V(19.55400,-0.53500,-0.63500),V(19.41600,-0.60900,-0.63500),V(19.26600,-0.65500,-0.63500),V(19.11000,-0.67000,-0.63500),V(18.95400,-0.65500,-0.63500),V(18.80400,-0.60900,-0.63500),V(18.66600,-0.53500,-0.63500),V(18.54400,-0.43600,-0.63500),V(18.44500,-0.31400,-0.63500),V(18.37100,-0.17600,-0.63500),V(18.32500,-0.02600,-0.63500),V(18.31000,0.13000,-0.63500),V(18.32500,0.28600,-0.63500),V(18.37100,0.43600,-0.63500),V(18.44500,0.57400,-0.63500),V(18.54400,0.69600,-0.63500),V(18.66600,0.79500,-0.63500),V(18.80400,0.86900,-0.63500),V(18.95400,0.91500,-0.63500),V(19.11000,0.93000,-0.63500),V(19.26600,0.91500,-0.63500),V(19.41600,0.86900,-0.63500),V(19.55400,0.79500,-0.63500),V(19.67600,0.69600,-0.63500),V(19.77500,0.57400,-0.63500),V(19.84900,0.43600,-0.63500),V(19.89500,0.28600,-0.63500),V(19.91000,0.13000,-0.63500),V(19.89500,-0.02600,-0.63500),V(19.84900,-0.17600,-0.63500),V(19.77500,-0.31400,-0.63500),V(19.67600,-0.43600,-0.63500),V(19.55400,-0.53500,-0.63500)])]).extrude(V(0,0,0.69900)))
_s.append(Part.Face([_poly([V(22.09400,-0.53500,-0.63500),V(21.95600,-0.60900,-0.63500),V(21.80600,-0.65500,-0.63500),V(21.65000,-0.67000,-0.63500),V(21.49400,-0.65500,-0.63500),V(21.34400,-0.60900,-0.63500),V(21.20600,-0.53500,-0.63500),V(21.08400,-0.43600,-0.63500),V(20.98500,-0.31400,-0.63500),V(20.91100,-0.17600,-0.63500),V(20.86500,-0.02600,-0.63500),V(20.85000,0.13000,-0.63500),V(20.86500,0.28600,-0.63500),V(20.91100,0.43600,-0.63500),V(20.98500,0.57400,-0.63500),V(21.08400,0.69600,-0.63500),V(21.20600,0.79500,-0.63500),V(21.34400,0.86900,-0.63500),V(21.49400,0.91500,-0.63500),V(21.65000,0.93000,-0.63500),V(21.80600,0.91500,-0.63500),V(21.95600,0.86900,-0.63500),V(22.09400,0.79500,-0.63500),V(22.21600,0.69600,-0.63500),V(22.31500,0.57400,-0.63500),V(22.38900,0.43600,-0.63500),V(22.43500,0.28600,-0.63500),V(22.45000,0.13000,-0.63500),V(22.43500,-0.02600,-0.63500),V(22.38900,-0.17600,-0.63500),V(22.31500,-0.31400,-0.63500),V(22.21600,-0.43600,-0.63500),V(22.09400,-0.53500,-0.63500)])]).extrude(V(0,0,0.69900)))
_s.append(Part.Face([_poly([V(24.49600,-0.60900,-0.63500),V(24.34600,-0.65500,-0.63500),V(24.19000,-0.67000,-0.63500),V(24.03400,-0.65500,-0.63500),V(23.88400,-0.60900,-0.63500),V(23.74600,-0.53500,-0.63500),V(23.62400,-0.43600,-0.63500),V(23.52500,-0.31400,-0.63500),V(23.45100,-0.17600,-0.63500),V(23.40500,-0.02600,-0.63500),V(23.39000,0.13000,-0.63500),V(23.40500,0.28600,-0.63500),V(23.45100,0.43600,-0.63500),V(23.52500,0.57400,-0.63500),V(23.62400,0.69600,-0.63500),V(23.74600,0.79500,-0.63500),V(23.88400,0.86900,-0.63500),V(24.03400,0.91500,-0.63500),V(24.19000,0.93000,-0.63500),V(24.34600,0.91500,-0.63500),V(24.49600,0.86900,-0.63500),V(24.63400,0.79500,-0.63500),V(24.75600,0.69600,-0.63500),V(24.85500,0.57400,-0.63500),V(24.92900,0.43600,-0.63500),V(24.97500,0.28600,-0.63500),V(24.99000,0.13000,-0.63500),V(24.97500,-0.02600,-0.63500),V(24.92900,-0.17600,-0.63500),V(24.85500,-0.31400,-0.63500),V(24.75600,-0.43600,-0.63500),V(24.63400,-0.53500,-0.63500),V(24.49600,-0.60900,-0.63500)])]).extrude(V(0,0,0.69900)))
_s.append(Part.Face([_poly([V(27.03600,-0.60900,-0.63500),V(26.88600,-0.65500,-0.63500),V(26.73000,-0.67000,-0.63500),V(26.57400,-0.65500,-0.63500),V(26.42400,-0.60900,-0.63500),V(26.28600,-0.53500,-0.63500),V(26.16400,-0.43600,-0.63500),V(26.06500,-0.31400,-0.63500),V(25.99100,-0.17600,-0.63500),V(25.94500,-0.02600,-0.63500),V(25.93000,0.13000,-0.63500),V(25.94500,0.28600,-0.63500),V(25.99100,0.43600,-0.63500),V(26.06500,0.57400,-0.63500),V(26.16400,0.69600,-0.63500),V(26.28600,0.79500,-0.63500),V(26.42400,0.86900,-0.63500),V(26.57400,0.91500,-0.63500),V(26.73000,0.93000,-0.63500),V(26.88600,0.91500,-0.63500),V(27.03600,0.86900,-0.63500),V(27.17400,0.79500,-0.63500),V(27.29600,0.69600,-0.63500),V(27.39500,0.57400,-0.63500),V(27.46900,0.43600,-0.63500),V(27.51500,0.28600,-0.63500),V(27.53000,0.13000,-0.63500),V(27.51500,-0.02600,-0.63500),V(27.46900,-0.17600,-0.63500),V(27.39500,-0.31400,-0.63500),V(27.29600,-0.43600,-0.63500),V(27.17400,-0.53500,-0.63500),V(27.03600,-0.60900,-0.63500)])]).extrude(V(0,0,0.69900)))
_s.append(Part.Face([_poly([V(29.71400,-0.53500,-0.63500),V(29.57600,-0.60900,-0.63500),V(29.42600,-0.65500,-0.63500),V(29.27000,-0.67000,-0.63500),V(29.11400,-0.65500,-0.63500),V(28.96400,-0.60900,-0.63500),V(28.82600,-0.53500,-0.63500),V(28.70400,-0.43600,-0.63500),V(28.60500,-0.31400,-0.63500),V(28.53100,-0.17600,-0.63500),V(28.48500,-0.02600,-0.63500),V(28.47000,0.13000,-0.63500),V(28.48500,0.28600,-0.63500),V(28.53100,0.43600,-0.63500),V(28.60500,0.57400,-0.63500),V(28.70400,0.69600,-0.63500),V(28.82600,0.79500,-0.63500),V(28.96400,0.86900,-0.63500),V(29.11400,0.91500,-0.63500),V(29.27000,0.93000,-0.63500),V(29.42600,0.91500,-0.63500),V(29.57600,0.86900,-0.63500),V(29.71400,0.79500,-0.63500),V(29.83600,0.69600,-0.63500),V(29.93500,0.57400,-0.63500),V(30.00900,0.43600,-0.63500),V(30.05500,0.28600,-0.63500),V(30.07000,0.13000,-0.63500),V(30.05500,-0.02600,-0.63500),V(30.00900,-0.17600,-0.63500),V(29.93500,-0.31400,-0.63500),V(29.83600,-0.43600,-0.63500),V(29.71400,-0.53500,-0.63500)])]).extrude(V(0,0,0.69900)))
_s.append(Part.Face([_poly([V(32.25400,-0.53500,-0.63500),V(32.11600,-0.60900,-0.63500),V(31.96600,-0.65500,-0.63500),V(31.81000,-0.67000,-0.63500),V(31.65400,-0.65500,-0.63500),V(31.50400,-0.60900,-0.63500),V(31.36600,-0.53500,-0.63500),V(31.24400,-0.43600,-0.63500),V(31.14500,-0.31400,-0.63500),V(31.07100,-0.17600,-0.63500),V(31.02500,-0.02600,-0.63500),V(31.01000,0.13000,-0.63500),V(31.02500,0.28600,-0.63500),V(31.07100,0.43600,-0.63500),V(31.14500,0.57400,-0.63500),V(31.24400,0.69600,-0.63500),V(31.36600,0.79500,-0.63500),V(31.50400,0.86900,-0.63500),V(31.65400,0.91500,-0.63500),V(31.81000,0.93000,-0.63500),V(31.96600,0.91500,-0.63500),V(32.11600,0.86900,-0.63500),V(32.25400,0.79500,-0.63500),V(32.37600,0.69600,-0.63500),V(32.47500,0.57400,-0.63500),V(32.54900,0.43600,-0.63500),V(32.59500,0.28600,-0.63500),V(32.61000,0.13000,-0.63500),V(32.59500,-0.02600,-0.63500),V(32.54900,-0.17600,-0.63500),V(32.47500,-0.31400,-0.63500),V(32.37600,-0.43600,-0.63500),V(32.25400,-0.53500,-0.63500)])]).extrude(V(0,0,0.69900)))
_s.append(Part.Face([_poly([V(34.79400,-0.53500,-0.63500),V(34.65600,-0.60900,-0.63500),V(34.50600,-0.65500,-0.63500),V(34.35000,-0.67000,-0.63500),V(34.19400,-0.65500,-0.63500),V(34.04400,-0.60900,-0.63500),V(33.90600,-0.53500,-0.63500),V(33.78400,-0.43600,-0.63500),V(33.68500,-0.31400,-0.63500),V(33.61100,-0.17600,-0.63500),V(33.56500,-0.02600,-0.63500),V(33.55000,0.13000,-0.63500),V(33.56500,0.28600,-0.63500),V(33.61100,0.43600,-0.63500),V(33.68500,0.57400,-0.63500),V(33.78400,0.69600,-0.63500),V(33.90600,0.79500,-0.63500),V(34.04400,0.86900,-0.63500),V(34.19400,0.91500,-0.63500),V(34.35000,0.93000,-0.63500),V(34.50600,0.91500,-0.63500),V(34.65600,0.86900,-0.63500),V(34.79400,0.79500,-0.63500),V(34.91600,0.69600,-0.63500),V(35.01500,0.57400,-0.63500),V(35.08900,0.43600,-0.63500),V(35.13500,0.28600,-0.63500),V(35.15000,0.13000,-0.63500),V(35.13500,-0.02600,-0.63500),V(35.08900,-0.17600,-0.63500),V(35.01500,-0.31400,-0.63500),V(34.91600,-0.43600,-0.63500),V(34.79400,-0.53500,-0.63500)])]).extrude(V(0,0,0.69900)))
_s.append(Part.Face([_poly([V(37.19600,-0.60900,-0.63500),V(37.04600,-0.65500,-0.63500),V(36.89000,-0.67000,-0.63500),V(36.73400,-0.65500,-0.63500),V(36.58400,-0.60900,-0.63500),V(36.44600,-0.53500,-0.63500),V(36.32400,-0.43600,-0.63500),V(36.22500,-0.31400,-0.63500),V(36.15100,-0.17600,-0.63500),V(36.10500,-0.02600,-0.63500),V(36.09000,0.13000,-0.63500),V(36.10500,0.28600,-0.63500),V(36.15100,0.43600,-0.63500),V(36.22500,0.57400,-0.63500),V(36.32400,0.69600,-0.63500),V(36.44600,0.79500,-0.63500),V(36.58400,0.86900,-0.63500),V(36.73400,0.91500,-0.63500),V(36.89000,0.93000,-0.63500),V(37.04600,0.91500,-0.63500),V(37.19600,0.86900,-0.63500),V(37.33400,0.79500,-0.63500),V(37.45600,0.69600,-0.63500),V(37.55500,0.57400,-0.63500),V(37.62900,0.43600,-0.63500),V(37.67500,0.28600,-0.63500),V(37.69000,0.13000,-0.63500),V(37.67500,-0.02600,-0.63500),V(37.62900,-0.17600,-0.63500),V(37.55500,-0.31400,-0.63500),V(37.45600,-0.43600,-0.63500),V(37.33400,-0.53500,-0.63500),V(37.19600,-0.60900,-0.63500)])]).extrude(V(0,0,0.69900)))
_s.append(Part.Face([_poly([V(39.73600,-0.60900,-0.63500),V(39.58600,-0.65500,-0.63500),V(39.43000,-0.67000,-0.63500),V(39.27400,-0.65500,-0.63500),V(39.12400,-0.60900,-0.63500),V(38.98600,-0.53500,-0.63500),V(38.86400,-0.43600,-0.63500),V(38.76500,-0.31400,-0.63500),V(38.69100,-0.17600,-0.63500),V(38.64500,-0.02600,-0.63500),V(38.63000,0.13000,-0.63500),V(38.64500,0.28600,-0.63500),V(38.69100,0.43600,-0.63500),V(38.76500,0.57400,-0.63500),V(38.86400,0.69600,-0.63500),V(38.98600,0.79500,-0.63500),V(39.12400,0.86900,-0.63500),V(39.27400,0.91500,-0.63500),V(39.43000,0.93000,-0.63500),V(39.58600,0.91500,-0.63500),V(39.73600,0.86900,-0.63500),V(39.87400,0.79500,-0.63500),V(39.99600,0.69600,-0.63500),V(40.09500,0.57400,-0.63500),V(40.16900,0.43600,-0.63500),V(40.21500,0.28600,-0.63500),V(40.23000,0.13000,-0.63500),V(40.21500,-0.02600,-0.63500),V(40.16900,-0.17600,-0.63500),V(40.09500,-0.31400,-0.63500),V(39.99600,-0.43600,-0.63500),V(39.87400,-0.53500,-0.63500),V(39.73600,-0.60900,-0.63500)])]).extrude(V(0,0,0.69900)))
_s.append(Part.Face([_poly([V(42.41400,-23.39500,-0.63500),V(42.27600,-23.46900,-0.63500),V(42.12600,-23.51500,-0.63500),V(41.97000,-23.53000,-0.63500),V(41.81400,-23.51500,-0.63500),V(41.66400,-23.46900,-0.63500),V(41.52600,-23.39500,-0.63500),V(41.40400,-23.29600,-0.63500),V(41.30500,-23.17400,-0.63500),V(41.23100,-23.03600,-0.63500),V(41.18500,-22.88600,-0.63500),V(41.17000,-22.73000,-0.63500),V(41.18500,-22.57400,-0.63500),V(41.23100,-22.42400,-0.63500),V(41.30500,-22.28600,-0.63500),V(41.40400,-22.16400,-0.63500),V(41.52600,-22.06500,-0.63500),V(41.66400,-21.99100,-0.63500),V(41.81400,-21.94500,-0.63500),V(41.97000,-21.93000,-0.63500),V(42.12600,-21.94500,-0.63500),V(42.27600,-21.99100,-0.63500),V(42.41400,-22.06500,-0.63500),V(42.53600,-22.16400,-0.63500),V(42.63500,-22.28600,-0.63500),V(42.70900,-22.42400,-0.63500),V(42.75500,-22.57400,-0.63500),V(42.77000,-22.73000,-0.63500),V(42.75500,-22.88600,-0.63500),V(42.70900,-23.03600,-0.63500),V(42.63500,-23.17400,-0.63500),V(42.53600,-23.29600,-0.63500),V(42.41400,-23.39500,-0.63500)])]).extrude(V(0,0,0.69900)))
_s.append(Part.Face([_poly([V(44.95400,-23.39500,-0.63500),V(44.81600,-23.46900,-0.63500),V(44.66600,-23.51500,-0.63500),V(44.51000,-23.53000,-0.63500),V(44.35400,-23.51500,-0.63500),V(44.20400,-23.46900,-0.63500),V(44.06600,-23.39500,-0.63500),V(43.94400,-23.29600,-0.63500),V(43.84500,-23.17400,-0.63500),V(43.77100,-23.03600,-0.63500),V(43.72500,-22.88600,-0.63500),V(43.71000,-22.73000,-0.63500),V(43.72500,-22.57400,-0.63500),V(43.77100,-22.42400,-0.63500),V(43.84500,-22.28600,-0.63500),V(43.94400,-22.16400,-0.63500),V(44.06600,-22.06500,-0.63500),V(44.20400,-21.99100,-0.63500),V(44.35400,-21.94500,-0.63500),V(44.51000,-21.93000,-0.63500),V(44.66600,-21.94500,-0.63500),V(44.81600,-21.99100,-0.63500),V(44.95400,-22.06500,-0.63500),V(45.07600,-22.16400,-0.63500),V(45.17500,-22.28600,-0.63500),V(45.24900,-22.42400,-0.63500),V(45.29500,-22.57400,-0.63500),V(45.31000,-22.73000,-0.63500),V(45.29500,-22.88600,-0.63500),V(45.24900,-23.03600,-0.63500),V(45.17500,-23.17400,-0.63500),V(45.07600,-23.29600,-0.63500),V(44.95400,-23.39500,-0.63500)])]).extrude(V(0,0,0.69900)))
_s.append(Part.Face([_poly([V(47.49400,-23.39500,-0.63500),V(47.35600,-23.46900,-0.63500),V(47.20600,-23.51500,-0.63500),V(47.05000,-23.53000,-0.63500),V(46.89400,-23.51500,-0.63500),V(46.74400,-23.46900,-0.63500),V(46.60600,-23.39500,-0.63500),V(46.48400,-23.29600,-0.63500),V(46.38500,-23.17400,-0.63500),V(46.31100,-23.03600,-0.63500),V(46.26500,-22.88600,-0.63500),V(46.25000,-22.73000,-0.63500),V(46.26500,-22.57400,-0.63500),V(46.31100,-22.42400,-0.63500),V(46.38500,-22.28600,-0.63500),V(46.48400,-22.16400,-0.63500),V(46.60600,-22.06500,-0.63500),V(46.74400,-21.99100,-0.63500),V(46.89400,-21.94500,-0.63500),V(47.05000,-21.93000,-0.63500),V(47.20600,-21.94500,-0.63500),V(47.35600,-21.99100,-0.63500),V(47.49400,-22.06500,-0.63500),V(47.61600,-22.16400,-0.63500),V(47.71500,-22.28600,-0.63500),V(47.78900,-22.42400,-0.63500),V(47.83500,-22.57400,-0.63500),V(47.85000,-22.73000,-0.63500),V(47.83500,-22.88600,-0.63500),V(47.78900,-23.03600,-0.63500),V(47.71500,-23.17400,-0.63500),V(47.61600,-23.29600,-0.63500),V(47.49400,-23.39500,-0.63500)])]).extrude(V(0,0,0.69900)))
_s.append(Part.Face([_poly([V(49.89600,-23.46900,-0.63500),V(49.74600,-23.51500,-0.63500),V(49.59000,-23.53000,-0.63500),V(49.43400,-23.51500,-0.63500),V(49.28400,-23.46900,-0.63500),V(49.14600,-23.39500,-0.63500),V(49.02400,-23.29600,-0.63500),V(48.92500,-23.17400,-0.63500),V(48.85100,-23.03600,-0.63500),V(48.80500,-22.88600,-0.63500),V(48.79000,-22.73000,-0.63500),V(48.80500,-22.57400,-0.63500),V(48.85100,-22.42400,-0.63500),V(48.92500,-22.28600,-0.63500),V(49.02400,-22.16400,-0.63500),V(49.14600,-22.06500,-0.63500),V(49.28400,-21.99100,-0.63500),V(49.43400,-21.94500,-0.63500),V(49.59000,-21.93000,-0.63500),V(49.74600,-21.94500,-0.63500),V(49.89600,-21.99100,-0.63500),V(50.03400,-22.06500,-0.63500),V(50.15600,-22.16400,-0.63500),V(50.25500,-22.28600,-0.63500),V(50.32900,-22.42400,-0.63500),V(50.37500,-22.57400,-0.63500),V(50.39000,-22.73000,-0.63500),V(50.37500,-22.88600,-0.63500),V(50.32900,-23.03600,-0.63500),V(50.25500,-23.17400,-0.63500),V(50.15600,-23.29600,-0.63500),V(50.03400,-23.39500,-0.63500),V(49.89600,-23.46900,-0.63500)])]).extrude(V(0,0,0.69900)))
_s.append(Part.Face([_poly([V(52.43600,-23.46900,-0.63500),V(52.28600,-23.51500,-0.63500),V(52.13000,-23.53000,-0.63500),V(51.97400,-23.51500,-0.63500),V(51.82400,-23.46900,-0.63500),V(51.68600,-23.39500,-0.63500),V(51.56400,-23.29600,-0.63500),V(51.46500,-23.17400,-0.63500),V(51.39100,-23.03600,-0.63500),V(51.34500,-22.88600,-0.63500),V(51.33000,-22.73000,-0.63500),V(51.34500,-22.57400,-0.63500),V(51.39100,-22.42400,-0.63500),V(51.46500,-22.28600,-0.63500),V(51.56400,-22.16400,-0.63500),V(51.68600,-22.06500,-0.63500),V(51.82400,-21.99100,-0.63500),V(51.97400,-21.94500,-0.63500),V(52.13000,-21.93000,-0.63500),V(52.28600,-21.94500,-0.63500),V(52.43600,-21.99100,-0.63500),V(52.57400,-22.06500,-0.63500),V(52.69600,-22.16400,-0.63500),V(52.79500,-22.28600,-0.63500),V(52.86900,-22.42400,-0.63500),V(52.91500,-22.57400,-0.63500),V(52.93000,-22.73000,-0.63500),V(52.91500,-22.88600,-0.63500),V(52.86900,-23.03600,-0.63500),V(52.79500,-23.17400,-0.63500),V(52.69600,-23.29600,-0.63500),V(52.57400,-23.39500,-0.63500),V(52.43600,-23.46900,-0.63500)])]).extrude(V(0,0,0.69900)))
_s.append(Part.Face([_poly([V(55.11400,-23.39500,-0.63500),V(54.97600,-23.46900,-0.63500),V(54.82600,-23.51500,-0.63500),V(54.67000,-23.53000,-0.63500),V(54.51400,-23.51500,-0.63500),V(54.36400,-23.46900,-0.63500),V(54.22600,-23.39500,-0.63500),V(54.10400,-23.29600,-0.63500),V(54.00500,-23.17400,-0.63500),V(53.93100,-23.03600,-0.63500),V(53.88500,-22.88600,-0.63500),V(53.87000,-22.73000,-0.63500),V(53.88500,-22.57400,-0.63500),V(53.93100,-22.42400,-0.63500),V(54.00500,-22.28600,-0.63500),V(54.10400,-22.16400,-0.63500),V(54.22600,-22.06500,-0.63500),V(54.36400,-21.99100,-0.63500),V(54.51400,-21.94500,-0.63500),V(54.67000,-21.93000,-0.63500),V(54.82600,-21.94500,-0.63500),V(54.97600,-21.99100,-0.63500),V(55.11400,-22.06500,-0.63500),V(55.23600,-22.16400,-0.63500),V(55.33500,-22.28600,-0.63500),V(55.40900,-22.42400,-0.63500),V(55.45500,-22.57400,-0.63500),V(55.47000,-22.73000,-0.63500),V(55.45500,-22.88600,-0.63500),V(55.40900,-23.03600,-0.63500),V(55.33500,-23.17400,-0.63500),V(55.23600,-23.29600,-0.63500),V(55.11400,-23.39500,-0.63500)])]).extrude(V(0,0,0.69900)))
_s.append(Part.Face([_poly([V(57.65400,-23.39500,-0.63500),V(57.51600,-23.46900,-0.63500),V(57.36600,-23.51500,-0.63500),V(57.21000,-23.53000,-0.63500),V(57.05400,-23.51500,-0.63500),V(56.90400,-23.46900,-0.63500),V(56.76600,-23.39500,-0.63500),V(56.64400,-23.29600,-0.63500),V(56.54500,-23.17400,-0.63500),V(56.47100,-23.03600,-0.63500),V(56.42500,-22.88600,-0.63500),V(56.41000,-22.73000,-0.63500),V(56.42500,-22.57400,-0.63500),V(56.47100,-22.42400,-0.63500),V(56.54500,-22.28600,-0.63500),V(56.64400,-22.16400,-0.63500),V(56.76600,-22.06500,-0.63500),V(56.90400,-21.99100,-0.63500),V(57.05400,-21.94500,-0.63500),V(57.21000,-21.93000,-0.63500),V(57.36600,-21.94500,-0.63500),V(57.51600,-21.99100,-0.63500),V(57.65400,-22.06500,-0.63500),V(57.77600,-22.16400,-0.63500),V(57.87500,-22.28600,-0.63500),V(57.94900,-22.42400,-0.63500),V(57.99500,-22.57400,-0.63500),V(58.01000,-22.73000,-0.63500),V(57.99500,-22.88600,-0.63500),V(57.94900,-23.03600,-0.63500),V(57.87500,-23.17400,-0.63500),V(57.77600,-23.29600,-0.63500),V(57.65400,-23.39500,-0.63500)])]).extrude(V(0,0,0.69900)))
_s.append(Part.Face([_poly([V(60.19400,-23.39500,-0.63500),V(60.05600,-23.46900,-0.63500),V(59.90600,-23.51500,-0.63500),V(59.75000,-23.53000,-0.63500),V(59.59400,-23.51500,-0.63500),V(59.44400,-23.46900,-0.63500),V(59.30600,-23.39500,-0.63500),V(59.18400,-23.29600,-0.63500),V(59.08500,-23.17400,-0.63500),V(59.01100,-23.03600,-0.63500),V(58.96500,-22.88600,-0.63500),V(58.95000,-22.73000,-0.63500),V(58.96500,-22.57400,-0.63500),V(59.01100,-22.42400,-0.63500),V(59.08500,-22.28600,-0.63500),V(59.18400,-22.16400,-0.63500),V(59.30600,-22.06500,-0.63500),V(59.44400,-21.99100,-0.63500),V(59.59400,-21.94500,-0.63500),V(59.75000,-21.93000,-0.63500),V(59.90600,-21.94500,-0.63500),V(60.05600,-21.99100,-0.63500),V(60.19400,-22.06500,-0.63500),V(60.31600,-22.16400,-0.63500),V(60.41500,-22.28600,-0.63500),V(60.48900,-22.42400,-0.63500),V(60.53500,-22.57400,-0.63500),V(60.55000,-22.73000,-0.63500),V(60.53500,-22.88600,-0.63500),V(60.48900,-23.03600,-0.63500),V(60.41500,-23.17400,-0.63500),V(60.31600,-23.29600,-0.63500),V(60.19400,-23.39500,-0.63500)])]).extrude(V(0,0,0.69900)))
_s.append(Part.Face([_poly([V(62.59600,-23.46900,-0.63500),V(62.44600,-23.51500,-0.63500),V(62.29000,-23.53000,-0.63500),V(62.13400,-23.51500,-0.63500),V(61.98400,-23.46900,-0.63500),V(61.84600,-23.39500,-0.63500),V(61.72400,-23.29600,-0.63500),V(61.62500,-23.17400,-0.63500),V(61.55100,-23.03600,-0.63500),V(61.50500,-22.88600,-0.63500),V(61.49000,-22.73000,-0.63500),V(61.50500,-22.57400,-0.63500),V(61.55100,-22.42400,-0.63500),V(61.62500,-22.28600,-0.63500),V(61.72400,-22.16400,-0.63500),V(61.84600,-22.06500,-0.63500),V(61.98400,-21.99100,-0.63500),V(62.13400,-21.94500,-0.63500),V(62.29000,-21.93000,-0.63500),V(62.44600,-21.94500,-0.63500),V(62.59600,-21.99100,-0.63500),V(62.73400,-22.06500,-0.63500),V(62.85600,-22.16400,-0.63500),V(62.95500,-22.28600,-0.63500),V(63.02900,-22.42400,-0.63500),V(63.07500,-22.57400,-0.63500),V(63.09000,-22.73000,-0.63500),V(63.07500,-22.88600,-0.63500),V(63.02900,-23.03600,-0.63500),V(62.95500,-23.17400,-0.63500),V(62.85600,-23.29600,-0.63500),V(62.73400,-23.39500,-0.63500),V(62.59600,-23.46900,-0.63500)])]).extrude(V(0,0,0.69900)))
_s.append(Part.Face([_poly([V(65.13600,-23.46900,-0.63500),V(64.98600,-23.51500,-0.63500),V(64.83000,-23.53000,-0.63500),V(64.67400,-23.51500,-0.63500),V(64.52400,-23.46900,-0.63500),V(64.38600,-23.39500,-0.63500),V(64.26400,-23.29600,-0.63500),V(64.16500,-23.17400,-0.63500),V(64.09100,-23.03600,-0.63500),V(64.04500,-22.88600,-0.63500),V(64.03000,-22.73000,-0.63500),V(64.04500,-22.57400,-0.63500),V(64.09100,-22.42400,-0.63500),V(64.16500,-22.28600,-0.63500),V(64.26400,-22.16400,-0.63500),V(64.38600,-22.06500,-0.63500),V(64.52400,-21.99100,-0.63500),V(64.67400,-21.94500,-0.63500),V(64.83000,-21.93000,-0.63500),V(64.98600,-21.94500,-0.63500),V(65.13600,-21.99100,-0.63500),V(65.27400,-22.06500,-0.63500),V(65.39600,-22.16400,-0.63500),V(65.49500,-22.28600,-0.63500),V(65.56900,-22.42400,-0.63500),V(65.61500,-22.57400,-0.63500),V(65.63000,-22.73000,-0.63500),V(65.61500,-22.88600,-0.63500),V(65.56900,-23.03600,-0.63500),V(65.49500,-23.17400,-0.63500),V(65.39600,-23.29600,-0.63500),V(65.27400,-23.39500,-0.63500),V(65.13600,-23.46900,-0.63500)])]).extrude(V(0,0,0.69900)))
_s.append(Part.Face([_poly([V(42.41400,-0.53500,-0.63500),V(42.27600,-0.60900,-0.63500),V(42.12600,-0.65500,-0.63500),V(41.97000,-0.67000,-0.63500),V(41.81400,-0.65500,-0.63500),V(41.66400,-0.60900,-0.63500),V(41.52600,-0.53500,-0.63500),V(41.40400,-0.43600,-0.63500),V(41.30500,-0.31400,-0.63500),V(41.23100,-0.17600,-0.63500),V(41.18500,-0.02600,-0.63500),V(41.17000,0.13000,-0.63500),V(41.18500,0.28600,-0.63500),V(41.23100,0.43600,-0.63500),V(41.30500,0.57400,-0.63500),V(41.40400,0.69600,-0.63500),V(41.52600,0.79500,-0.63500),V(41.66400,0.86900,-0.63500),V(41.81400,0.91500,-0.63500),V(41.97000,0.93000,-0.63500),V(42.12600,0.91500,-0.63500),V(42.27600,0.86900,-0.63500),V(42.41400,0.79500,-0.63500),V(42.53600,0.69600,-0.63500),V(42.63500,0.57400,-0.63500),V(42.70900,0.43600,-0.63500),V(42.75500,0.28600,-0.63500),V(42.77000,0.13000,-0.63500),V(42.75500,-0.02600,-0.63500),V(42.70900,-0.17600,-0.63500),V(42.63500,-0.31400,-0.63500),V(42.53600,-0.43600,-0.63500),V(42.41400,-0.53500,-0.63500)])]).extrude(V(0,0,0.69900)))
_s.append(Part.Face([_poly([V(44.95400,-0.53500,-0.63500),V(44.81600,-0.60900,-0.63500),V(44.66600,-0.65500,-0.63500),V(44.51000,-0.67000,-0.63500),V(44.35400,-0.65500,-0.63500),V(44.20400,-0.60900,-0.63500),V(44.06600,-0.53500,-0.63500),V(43.94400,-0.43600,-0.63500),V(43.84500,-0.31400,-0.63500),V(43.77100,-0.17600,-0.63500),V(43.72500,-0.02600,-0.63500),V(43.71000,0.13000,-0.63500),V(43.72500,0.28600,-0.63500),V(43.77100,0.43600,-0.63500),V(43.84500,0.57400,-0.63500),V(43.94400,0.69600,-0.63500),V(44.06600,0.79500,-0.63500),V(44.20400,0.86900,-0.63500),V(44.35400,0.91500,-0.63500),V(44.51000,0.93000,-0.63500),V(44.66600,0.91500,-0.63500),V(44.81600,0.86900,-0.63500),V(44.95400,0.79500,-0.63500),V(45.07600,0.69600,-0.63500),V(45.17500,0.57400,-0.63500),V(45.24900,0.43600,-0.63500),V(45.29500,0.28600,-0.63500),V(45.31000,0.13000,-0.63500),V(45.29500,-0.02600,-0.63500),V(45.24900,-0.17600,-0.63500),V(45.17500,-0.31400,-0.63500),V(45.07600,-0.43600,-0.63500),V(44.95400,-0.53500,-0.63500)])]).extrude(V(0,0,0.69900)))
_s.append(Part.Face([_poly([V(47.49400,-0.53500,-0.63500),V(47.35600,-0.60900,-0.63500),V(47.20600,-0.65500,-0.63500),V(47.05000,-0.67000,-0.63500),V(46.89400,-0.65500,-0.63500),V(46.74400,-0.60900,-0.63500),V(46.60600,-0.53500,-0.63500),V(46.48400,-0.43600,-0.63500),V(46.38500,-0.31400,-0.63500),V(46.31100,-0.17600,-0.63500),V(46.26500,-0.02600,-0.63500),V(46.25000,0.13000,-0.63500),V(46.26500,0.28600,-0.63500),V(46.31100,0.43600,-0.63500),V(46.38500,0.57400,-0.63500),V(46.48400,0.69600,-0.63500),V(46.60600,0.79500,-0.63500),V(46.74400,0.86900,-0.63500),V(46.89400,0.91500,-0.63500),V(47.05000,0.93000,-0.63500),V(47.20600,0.91500,-0.63500),V(47.35600,0.86900,-0.63500),V(47.49400,0.79500,-0.63500),V(47.61600,0.69600,-0.63500),V(47.71500,0.57400,-0.63500),V(47.78900,0.43600,-0.63500),V(47.83500,0.28600,-0.63500),V(47.85000,0.13000,-0.63500),V(47.83500,-0.02600,-0.63500),V(47.78900,-0.17600,-0.63500),V(47.71500,-0.31400,-0.63500),V(47.61600,-0.43600,-0.63500),V(47.49400,-0.53500,-0.63500)])]).extrude(V(0,0,0.69900)))
_s.append(Part.Face([_poly([V(49.89600,-0.60900,-0.63500),V(49.74600,-0.65500,-0.63500),V(49.59000,-0.67000,-0.63500),V(49.43400,-0.65500,-0.63500),V(49.28400,-0.60900,-0.63500),V(49.14600,-0.53500,-0.63500),V(49.02400,-0.43600,-0.63500),V(48.92500,-0.31400,-0.63500),V(48.85100,-0.17600,-0.63500),V(48.80500,-0.02600,-0.63500),V(48.79000,0.13000,-0.63500),V(48.80500,0.28600,-0.63500),V(48.85100,0.43600,-0.63500),V(48.92500,0.57400,-0.63500),V(49.02400,0.69600,-0.63500),V(49.14600,0.79500,-0.63500),V(49.28400,0.86900,-0.63500),V(49.43400,0.91500,-0.63500),V(49.59000,0.93000,-0.63500),V(49.74600,0.91500,-0.63500),V(49.89600,0.86900,-0.63500),V(50.03400,0.79500,-0.63500),V(50.15600,0.69600,-0.63500),V(50.25500,0.57400,-0.63500),V(50.32900,0.43600,-0.63500),V(50.37500,0.28600,-0.63500),V(50.39000,0.13000,-0.63500),V(50.37500,-0.02600,-0.63500),V(50.32900,-0.17600,-0.63500),V(50.25500,-0.31400,-0.63500),V(50.15600,-0.43600,-0.63500),V(50.03400,-0.53500,-0.63500),V(49.89600,-0.60900,-0.63500)])]).extrude(V(0,0,0.69900)))
_s.append(Part.Face([_poly([V(52.43600,-0.60900,-0.63500),V(52.28600,-0.65500,-0.63500),V(52.13000,-0.67000,-0.63500),V(51.97400,-0.65500,-0.63500),V(51.82400,-0.60900,-0.63500),V(51.68600,-0.53500,-0.63500),V(51.56400,-0.43600,-0.63500),V(51.46500,-0.31400,-0.63500),V(51.39100,-0.17600,-0.63500),V(51.34500,-0.02600,-0.63500),V(51.33000,0.13000,-0.63500),V(51.34500,0.28600,-0.63500),V(51.39100,0.43600,-0.63500),V(51.46500,0.57400,-0.63500),V(51.56400,0.69600,-0.63500),V(51.68600,0.79500,-0.63500),V(51.82400,0.86900,-0.63500),V(51.97400,0.91500,-0.63500),V(52.13000,0.93000,-0.63500),V(52.28600,0.91500,-0.63500),V(52.43600,0.86900,-0.63500),V(52.57400,0.79500,-0.63500),V(52.69600,0.69600,-0.63500),V(52.79500,0.57400,-0.63500),V(52.86900,0.43600,-0.63500),V(52.91500,0.28600,-0.63500),V(52.93000,0.13000,-0.63500),V(52.91500,-0.02600,-0.63500),V(52.86900,-0.17600,-0.63500),V(52.79500,-0.31400,-0.63500),V(52.69600,-0.43600,-0.63500),V(52.57400,-0.53500,-0.63500),V(52.43600,-0.60900,-0.63500)])]).extrude(V(0,0,0.69900)))
_s.append(Part.Face([_poly([V(55.11400,-0.53500,-0.63500),V(54.97600,-0.60900,-0.63500),V(54.82600,-0.65500,-0.63500),V(54.67000,-0.67000,-0.63500),V(54.51400,-0.65500,-0.63500),V(54.36400,-0.60900,-0.63500),V(54.22600,-0.53500,-0.63500),V(54.10400,-0.43600,-0.63500),V(54.00500,-0.31400,-0.63500),V(53.93100,-0.17600,-0.63500),V(53.88500,-0.02600,-0.63500),V(53.87000,0.13000,-0.63500),V(53.88500,0.28600,-0.63500),V(53.93100,0.43600,-0.63500),V(54.00500,0.57400,-0.63500),V(54.10400,0.69600,-0.63500),V(54.22600,0.79500,-0.63500),V(54.36400,0.86900,-0.63500),V(54.51400,0.91500,-0.63500),V(54.67000,0.93000,-0.63500),V(54.82600,0.91500,-0.63500),V(54.97600,0.86900,-0.63500),V(55.11400,0.79500,-0.63500),V(55.23600,0.69600,-0.63500),V(55.33500,0.57400,-0.63500),V(55.40900,0.43600,-0.63500),V(55.45500,0.28600,-0.63500),V(55.47000,0.13000,-0.63500),V(55.45500,-0.02600,-0.63500),V(55.40900,-0.17600,-0.63500),V(55.33500,-0.31400,-0.63500),V(55.23600,-0.43600,-0.63500),V(55.11400,-0.53500,-0.63500)])]).extrude(V(0,0,0.69900)))
_s.append(Part.Face([_poly([V(57.65400,-0.53500,-0.63500),V(57.51600,-0.60900,-0.63500),V(57.36600,-0.65500,-0.63500),V(57.21000,-0.67000,-0.63500),V(57.05400,-0.65500,-0.63500),V(56.90400,-0.60900,-0.63500),V(56.76600,-0.53500,-0.63500),V(56.64400,-0.43600,-0.63500),V(56.54500,-0.31400,-0.63500),V(56.47100,-0.17600,-0.63500),V(56.42500,-0.02600,-0.63500),V(56.41000,0.13000,-0.63500),V(56.42500,0.28600,-0.63500),V(56.47100,0.43600,-0.63500),V(56.54500,0.57400,-0.63500),V(56.64400,0.69600,-0.63500),V(56.76600,0.79500,-0.63500),V(56.90400,0.86900,-0.63500),V(57.05400,0.91500,-0.63500),V(57.21000,0.93000,-0.63500),V(57.36600,0.91500,-0.63500),V(57.51600,0.86900,-0.63500),V(57.65400,0.79500,-0.63500),V(57.77600,0.69600,-0.63500),V(57.87500,0.57400,-0.63500),V(57.94900,0.43600,-0.63500),V(57.99500,0.28600,-0.63500),V(58.01000,0.13000,-0.63500),V(57.99500,-0.02600,-0.63500),V(57.94900,-0.17600,-0.63500),V(57.87500,-0.31400,-0.63500),V(57.77600,-0.43600,-0.63500),V(57.65400,-0.53500,-0.63500)])]).extrude(V(0,0,0.69900)))
_s.append(Part.Face([_poly([V(60.19400,-0.53500,-0.63500),V(60.05600,-0.60900,-0.63500),V(59.90600,-0.65500,-0.63500),V(59.75000,-0.67000,-0.63500),V(59.59400,-0.65500,-0.63500),V(59.44400,-0.60900,-0.63500),V(59.30600,-0.53500,-0.63500),V(59.18400,-0.43600,-0.63500),V(59.08500,-0.31400,-0.63500),V(59.01100,-0.17600,-0.63500),V(58.96500,-0.02600,-0.63500),V(58.95000,0.13000,-0.63500),V(58.96500,0.28600,-0.63500),V(59.01100,0.43600,-0.63500),V(59.08500,0.57400,-0.63500),V(59.18400,0.69600,-0.63500),V(59.30600,0.79500,-0.63500),V(59.44400,0.86900,-0.63500),V(59.59400,0.91500,-0.63500),V(59.75000,0.93000,-0.63500),V(59.90600,0.91500,-0.63500),V(60.05600,0.86900,-0.63500),V(60.19400,0.79500,-0.63500),V(60.31600,0.69600,-0.63500),V(60.41500,0.57400,-0.63500),V(60.48900,0.43600,-0.63500),V(60.53500,0.28600,-0.63500),V(60.55000,0.13000,-0.63500),V(60.53500,-0.02600,-0.63500),V(60.48900,-0.17600,-0.63500),V(60.41500,-0.31400,-0.63500),V(60.31600,-0.43600,-0.63500),V(60.19400,-0.53500,-0.63500)])]).extrude(V(0,0,0.69900)))
_s.append(Part.Face([_poly([V(62.59600,-0.60900,-0.63500),V(62.44600,-0.65500,-0.63500),V(62.29000,-0.67000,-0.63500),V(62.13400,-0.65500,-0.63500),V(61.98400,-0.60900,-0.63500),V(61.84600,-0.53500,-0.63500),V(61.72400,-0.43600,-0.63500),V(61.62500,-0.31400,-0.63500),V(61.55100,-0.17600,-0.63500),V(61.50500,-0.02600,-0.63500),V(61.49000,0.13000,-0.63500),V(61.50500,0.28600,-0.63500),V(61.55100,0.43600,-0.63500),V(61.62500,0.57400,-0.63500),V(61.72400,0.69600,-0.63500),V(61.84600,0.79500,-0.63500),V(61.98400,0.86900,-0.63500),V(62.13400,0.91500,-0.63500),V(62.29000,0.93000,-0.63500),V(62.44600,0.91500,-0.63500),V(62.59600,0.86900,-0.63500),V(62.73400,0.79500,-0.63500),V(62.85600,0.69600,-0.63500),V(62.95500,0.57400,-0.63500),V(63.02900,0.43600,-0.63500),V(63.07500,0.28600,-0.63500),V(63.09000,0.13000,-0.63500),V(63.07500,-0.02600,-0.63500),V(63.02900,-0.17600,-0.63500),V(62.95500,-0.31400,-0.63500),V(62.85600,-0.43600,-0.63500),V(62.73400,-0.53500,-0.63500),V(62.59600,-0.60900,-0.63500)])]).extrude(V(0,0,0.69900)))
_s.append(Part.Face([_poly([V(65.13600,-0.60900,-0.63500),V(64.98600,-0.65500,-0.63500),V(64.83000,-0.67000,-0.63500),V(64.67400,-0.65500,-0.63500),V(64.52400,-0.60900,-0.63500),V(64.38600,-0.53500,-0.63500),V(64.26400,-0.43600,-0.63500),V(64.16500,-0.31400,-0.63500),V(64.09100,-0.17600,-0.63500),V(64.04500,-0.02600,-0.63500),V(64.03000,0.13000,-0.63500),V(64.04500,0.28600,-0.63500),V(64.09100,0.43600,-0.63500),V(64.16500,0.57400,-0.63500),V(64.26400,0.69600,-0.63500),V(64.38600,0.79500,-0.63500),V(64.52400,0.86900,-0.63500),V(64.67400,0.91500,-0.63500),V(64.83000,0.93000,-0.63500),V(64.98600,0.91500,-0.63500),V(65.13600,0.86900,-0.63500),V(65.27400,0.79500,-0.63500),V(65.39600,0.69600,-0.63500),V(65.49500,0.57400,-0.63500),V(65.56900,0.43600,-0.63500),V(65.61500,0.28600,-0.63500),V(65.63000,0.13000,-0.63500),V(65.61500,-0.02600,-0.63500),V(65.56900,-0.17600,-0.63500),V(65.49500,-0.31400,-0.63500),V(65.39600,-0.43600,-0.63500),V(65.27400,-0.53500,-0.63500),V(65.13600,-0.60900,-0.63500)])]).extrude(V(0,0,0.69900)))
_add('L49' + '_L49', _fuse(_s), (0.5686,0.1176,0.7059), surface=True)
# --- substrate (layers [57]) : z -0.6350..0 mm ---
_s = []
_s.append(Part.Face([_poly([V(15.60000,-21.00000,-0.63500),V(66.00000,-21.00000,-0.63500),V(66.00000,-1.60000,-0.63500),V(15.60000,-1.60000,-0.63500),V(15.60000,-21.00000,-0.63500)])]).extrude(V(0,0,0.63500)))
_add('Substrate', _fuse(_s), (0.97, 0.97, 0.95), surface=True)
# --- component DIE_54AS181_U1 (extrude 0.3800 mm) ---
_sh = Part.Face(_poly([V(48.09000,-10.67000,0.00000),V(48.09000,-13.73000,0.00000),V(51.15000,-13.73000,0.00000),V(51.15000,-10.67000,0.00000),V(48.09000,-10.67000,0.00000)])).extrude(V(0,0,0.38000))
_sh.translate(V(0, 0, 0.05400))
_add('U1_DIE_54AS181_U1', _sh, (0.15,0.15,0.17))
# --- component DIE_54AS181_U2 (extrude 0.3800 mm) ---
_sh = Part.Face(_poly([V(36.65000,-9.92000,0.00000),V(33.59000,-9.92000,0.00000),V(33.59000,-12.98000,0.00000),V(36.65000,-12.98000,0.00000),V(36.65000,-9.92000,0.00000)])).extrude(V(0,0,0.38000))
_sh.translate(V(0, 0, 0.05400))
_add('U2_DIE_54AS181_U2', _sh, (0.15,0.15,0.17))
# --- component DIE_54LS27_U3 (extrude 0.3800 mm) ---
_sh = Part.Face(_poly([V(58.80500,-7.71500,0.00000),V(60.33500,-7.71500,0.00000),V(60.33500,-6.18500,0.00000),V(58.80500,-6.18500,0.00000),V(58.80500,-7.71500,0.00000)])).extrude(V(0,0,0.38000))
_sh.translate(V(0, 0, 0.05400))
_add('U3_DIE_54LS27_U3', _sh, (0.15,0.15,0.17))
# --- component DIE_54LS30_U4 (extrude 0.3800 mm) ---
_sh = Part.Face(_poly([V(59.70500,-16.36500,0.00000),V(61.23500,-16.36500,0.00000),V(61.23500,-14.83500,0.00000),V(59.70500,-14.83500,0.00000),V(59.70500,-16.36500,0.00000)])).extrude(V(0,0,0.38000))
_sh.translate(V(0, 0, 0.05400))
_add('U4_DIE_54LS30_U4', _sh, (0.15,0.15,0.17))
# --- component DIE_54LS86_U5 (extrude 0.3800 mm) ---
_sh = Part.Face(_poly([V(24.63500,-5.08500,0.00000),V(23.10500,-5.08500,0.00000),V(23.10500,-6.61500,0.00000),V(24.63500,-6.61500,0.00000),V(24.63500,-5.08500,0.00000)])).extrude(V(0,0,0.38000))
_sh.translate(V(0, 0, 0.05400))
_add('U5_DIE_54LS86_U5', _sh, (0.15,0.15,0.17))
# --- component DIE_54LS00_U6 (extrude 0.3800 mm) ---
_sh = Part.Face(_poly([V(20.70500,-14.03500,0.00000),V(20.70500,-15.56500,0.00000),V(22.23500,-15.56500,0.00000),V(22.23500,-14.03500,0.00000),V(20.70500,-14.03500,0.00000)])).extrude(V(0,0,0.38000))
_sh.translate(V(0, 0, 0.05400))
_add('U6_DIE_54LS00_U6', _sh, (0.15,0.15,0.17))
# --- package KOVAR_DIP40 (base under the substrate) ---
_sh = Part.Face(_poly([V(13.25000,-25.35000,0.00000),V(68.15000,-25.35000,0.00000),V(68.15000,2.75000,0.00000),V(13.25000,2.75000,0.00000),V(13.25000,-25.35000,0.00000)])).extrude(V(0,0,0.50000))
_sh.translate(V(0, 0, -1.13500))
_add('KOVAR_DIP40_1', _sh, (0.54, 0.56, 0.59))
# --- wire bonds (layers [59, 60]) ---
_BONDS = [
    (50.97000, -11.40000, 52.62000, -10.92500, 0.01500),
    (50.97000, -11.00000, 52.62000, -10.07500, 0.01500),
    (50.82000, -10.85000, 51.74500, -9.20000, 0.01500),
    (50.42000, -10.85000, 50.89500, -9.20000, 0.01500),
    (50.02000, -10.85000, 50.04500, -9.20000, 0.01500),
    (49.22000, -10.85000, 49.19500, -9.20000, 0.01500),
    (48.42000, -10.85000, 47.49500, -9.20000, 0.01500),
    (48.27000, -11.00000, 46.62000, -10.07500, 0.01500),
    (48.27000, -11.40000, 46.62000, -10.92500, 0.01500),
    (48.27000, -11.80000, 46.62000, -11.77500, 0.01500),
    (48.27000, -12.60000, 46.62000, -12.62500, 0.01500),
    (48.42000, -13.55000, 47.49500, -15.20000, 0.01500),
    (50.02000, -13.55000, 50.04500, -15.20000, 0.01500),
    (50.82000, -13.55000, 51.74500, -15.20000, 0.01500),
    (50.97000, -13.00000, 52.62000, -13.47500, 0.01500),
    (50.97000, -12.60000, 52.62000, -12.62500, 0.01500),
    (35.92000, -12.80000, 36.39500, -14.45000, 0.01500),
    (36.32000, -12.80000, 37.24500, -14.45000, 0.01500),
    (36.47000, -12.65000, 38.12000, -13.57500, 0.01500),
    (36.47000, -12.25000, 38.12000, -12.72500, 0.01500),
    (36.47000, -11.85000, 38.12000, -11.87500, 0.01500),
    (36.47000, -11.05000, 38.12000, -11.02500, 0.01500),
    (36.47000, -10.25000, 38.12000, -9.32500, 0.01500),
    (36.32000, -10.10000, 37.24500, -8.45000, 0.01500),
    (35.92000, -10.10000, 36.39500, -8.45000, 0.01500),
    (35.52000, -10.10000, 35.54500, -8.45000, 0.01500),
    (34.72000, -10.10000, 34.69500, -8.45000, 0.01500),
    (33.77000, -10.25000, 32.12000, -9.32500, 0.01500),
    (33.77000, -11.85000, 32.12000, -11.87500, 0.01500),
    (33.77000, -12.65000, 32.12000, -13.57500, 0.01500),
    (34.32000, -12.80000, 33.84500, -14.45000, 0.01500),
    (34.72000, -12.80000, 34.69500, -14.45000, 0.01500),
    (59.12000, -6.35000, 58.22000, -4.70000, 0.01500),
    (58.97000, -6.50000, 57.32000, -6.05000, 0.01500),
    (58.97000, -6.95000, 57.32000, -6.95000, 0.01500),
    (59.12000, -7.55000, 58.22000, -9.20000, 0.01500),
    (59.79500, -7.55000, 60.02000, -9.20000, 0.01500),
    (60.02000, -7.55000, 60.92000, -9.20000, 0.01500),
    (60.17000, -7.40000, 61.82000, -7.85000, 0.01500),
    (60.17000, -6.50000, 61.82000, -6.05000, 0.01500),
    (60.02000, -6.35000, 60.92000, -4.70000, 0.01500),
    (59.79500, -6.35000, 60.02000, -4.70000, 0.01500),
    (60.02000, -15.00000, 59.47000, -13.35000, 0.01500),
    (59.87000, -15.15000, 58.22000, -14.60000, 0.01500),
    (59.87000, -15.60000, 58.22000, -15.60000, 0.01500),
    (60.02000, -16.20000, 59.47000, -17.85000, 0.01500),
    (60.69500, -16.20000, 61.47000, -17.85000, 0.01500),
    (61.07000, -15.15000, 62.72000, -15.10000, 0.01500),
    (24.32000, -6.45000, 25.22000, -8.10000, 0.01500),
    (24.47000, -6.30000, 26.12000, -6.75000, 0.01500),
    (24.47000, -5.85000, 26.12000, -5.85000, 0.01500),
    (24.32000, -5.25000, 25.22000, -3.60000, 0.01500),
    (23.64500, -5.25000, 23.42000, -3.60000, 0.01500),
    (23.42000, -5.25000, 22.52000, -3.60000, 0.01500),
    (23.27000, -5.40000, 21.62000, -4.95000, 0.01500),
    (23.27000, -6.30000, 21.62000, -6.75000, 0.01500),
    (23.42000, -6.45000, 22.52000, -8.10000, 0.01500),
    (23.64500, -6.45000, 23.42000, -8.10000, 0.01500),
    (22.07000, -14.35000, 23.72000, -13.45000, 0.01500),
    (21.92000, -14.20000, 22.37000, -12.55000, 0.01500),
    (21.47000, -14.20000, 21.47000, -12.55000, 0.01500),
    (20.87000, -14.35000, 19.22000, -13.45000, 0.01500),
    (20.87000, -15.02500, 19.22000, -15.25000, 0.01500),
    (20.87000, -15.25000, 19.22000, -16.15000, 0.01500),
    (21.02000, -15.40000, 20.57000, -17.05000, 0.01500),
    (21.92000, -15.40000, 22.37000, -17.05000, 0.01500),
    (22.07000, -15.25000, 23.72000, -16.15000, 0.01500),
    (22.07000, -15.02500, 23.72000, -15.25000, 0.01500),
    (16.57000, -22.73000, 16.57000, -20.55000, 0.01500),
    (19.11000, -22.73000, 19.11000, -20.55000, 0.01500),
    (21.65000, -22.73000, 21.65000, -20.55000, 0.01500),
    (24.19000, -22.73000, 24.19000, -20.55000, 0.01500),
    (26.73000, -22.73000, 26.73000, -20.55000, 0.01500),
    (29.27000, -22.73000, 29.27000, -20.55000, 0.01500),
    (31.81000, -22.73000, 31.81000, -20.55000, 0.01500),
    (34.35000, -22.73000, 34.35000, -20.55000, 0.01500),
    (36.89000, -22.73000, 36.89000, -20.55000, 0.01500),
    (39.43000, -22.73000, 39.43000, -20.55000, 0.01500),
    (41.97000, -22.73000, 41.97000, -20.55000, 0.01500),
    (44.51000, -22.73000, 44.51000, -20.55000, 0.01500),
    (47.05000, -22.73000, 47.05000, -20.55000, 0.01500),
    (49.59000, -22.73000, 49.59000, -20.55000, 0.01500),
    (52.13000, -22.73000, 52.13000, -20.55000, 0.01500),
    (54.67000, -22.73000, 54.67000, -20.55000, 0.01500),
    (57.21000, -22.73000, 57.21000, -20.55000, 0.01500),
    (59.75000, -22.73000, 59.75000, -20.55000, 0.01500),
    (62.29000, -22.73000, 62.29000, -20.55000, 0.01500),
    (64.83000, -22.73000, 64.83000, -20.55000, 0.01500),
    (64.83000, 0.13000, 64.83000, -2.05000, 0.01500),
    (62.29000, 0.13000, 62.29000, -2.05000, 0.01500),
    (59.75000, 0.13000, 59.75000, -2.05000, 0.01500),
    (57.21000, 0.13000, 57.21000, -2.05000, 0.01500),
    (54.67000, 0.13000, 54.67000, -2.05000, 0.01500),
    (52.13000, 0.13000, 52.13000, -2.05000, 0.01500),
    (49.59000, 0.13000, 49.59000, -2.05000, 0.01500),
    (47.05000, 0.13000, 47.05000, -2.05000, 0.01500),
    (44.51000, 0.13000, 44.51000, -2.05000, 0.01500),
    (41.97000, 0.13000, 41.97000, -2.05000, 0.01500),
    (39.43000, 0.13000, 39.43000, -2.05000, 0.01500),
    (36.89000, 0.13000, 36.89000, -2.05000, 0.01500),
    (34.35000, 0.13000, 34.35000, -2.05000, 0.01500),
    (31.81000, 0.13000, 31.81000, -2.05000, 0.01500),
    (29.27000, 0.13000, 29.27000, -2.05000, 0.01500),
    (26.73000, 0.13000, 26.73000, -2.05000, 0.01500),
    (16.57000, 0.13000, 16.57000, -2.05000, 0.01500),
]
_bw = []
for _x0, _y0, _x1, _y1, _r in _BONDS:
    _z0 = _top_z(_x0, _y0, default=0.0)
    _z1 = _top_z(_x1, _y1, default=0.0)
    _za = max(_z0, _z1) + 0.25000
    _bw.append(_bondwire(V(_x0, _y0, _z0), V((_x0 + _x1) / 2.0, (_y0 + _y1) / 2.0, _za), V(_x1, _y1, _z1), _r))
_add('wire_bonds', _fuse(_bw), (0.9020,0.7451,1.0000))

_doc.recompute()
if _GUI:
    try:
        FreeCADGui.activeDocument().activeView().viewIsometric()
        FreeCADGui.SendMsgToActiveView("ViewFit")
    except Exception:
        pass
