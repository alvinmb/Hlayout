# FreeCAD 3D view of UNTITLED  (cell TOP)
# Generated by HLayout -- run inside FreeCAD: Macro > Macros... > Execute,
# or  freecadcmd this_file.FCMacro
import FreeCAD as App
import Part
from functools import reduce
_GUI = bool(getattr(App, "GuiUp", False))
if _GUI:
    import FreeCADGui

V = App.Vector
_doc = App.newDocument('UNTITLED_TOP')


def _poly(points):
    return Part.makePolygon(points)


def _fuse(solids):
    # A compound, not a boolean fuse: every layer's polygons were already
    # merged (shapely unary_union) before being written here, so the
    # solids are disjoint and fusing them is pure cost -- a sequential
    # BRep fuse of ~100 many-vertex traces took minutes and looked like
    # a hang. A compound renders, exports and section-probes the same.
    solids = [s for s in solids if s is not None and not s.isNull()]
    if not solids:
        return None
    return solids[0] if len(solids) == 1 else Part.makeCompound(solids)


#: shapes bonds and parts land on: _SURF = films + substrate (what a
#: component sits on), _PROBE = everything solid so far (what a bond
#: end lands on -- die pads, header pins, traces).
_SURF = []
_PROBE = []


def _parts(shape):
    """A shape's individual solids (or the shape itself) -- what the
    probes below test one by one, so their bounding-box prefilter skips
    almost everything instead of sectioning a whole layer compound."""
    try:
        sol = list(shape.Solids)
    except Exception:
        sol = []
    return sol or [shape]


def _add(name, shape, rgb, surface=False, transparency=0):
    if shape is None:
        return None
    o = _doc.addObject("Part::Feature", name)
    o.Shape = shape
    if _GUI and o.ViewObject is not None:
        o.ViewObject.ShapeColor = rgb
        if transparency:
            o.ViewObject.Transparency = int(transparency)
    _PROBE.extend(_parts(o.Shape))
    if surface:
        _SURF.extend(_parts(o.Shape))
    return o


def _top_z(x, y, shapes=None, default=None):
    """Highest solid surface straight below/at (x, y), or `default`."""
    best = None
    for sh in (_PROBE if shapes is None else shapes):
        bb = sh.BoundBox
        if not (bb.XMin - 1e-6 <= x <= bb.XMax + 1e-6 and bb.YMin - 1e-6 <= y <= bb.YMax + 1e-6):
            continue
        try:
            sec = sh.section(Part.makeLine(V(x, y, bb.ZMax + 1.0), V(x, y, bb.ZMin - 1.0)))
        except Exception:
            continue
        for v in sec.Vertexes:
            if best is None or v.Point.z > best:
                best = v.Point.z
    return default if best is None else best


def _surface_z(x0, y0, x1, y1):
    """Where a part with footprint (x0,y0)-(x1,y1) rests: the highest
    film/substrate top under its centre or inset corners (0 if none)."""
    ix, iy = (x1 - x0) * 0.2, (y1 - y0) * 0.2
    pts = [((x0 + x1) / 2.0, (y0 + y1) / 2.0), (x0 + ix, y0 + iy), (x1 - ix, y0 + iy),
           (x1 - ix, y1 - iy), (x0 + ix, y1 - iy)]
    zs = [_top_z(x, y, _SURF) for x, y in pts]
    zs = [z for z in zs if z is not None]
    return max(zs) if zs else 0.0


_MODEL_SHAPES = {}     # path -> shape read once (probing + headless/mirrored use)
_MODEL_TEMPLATES = {}  # path -> first coloured GUI import, re-used via App::Link


def _progress(msg):
    """Report progress and keep the FreeCAD window painting while the
    macro runs -- otherwise a long GUI run looks frozen ("Not
    Responding") although it is still working."""
    App.Console.PrintMessage("HLayout: %s\n" % msg)
    if _GUI:
        try:
            FreeCADGui.updateGui()
        except Exception:
            pass


def _model_shape(path):
    sh = _MODEL_SHAPES.get(path)
    if sh is None:
        sh = Part.Shape()
        sh.read(path)
        _MODEL_SHAPES[path] = sh
    return sh


def _place_model(path, name, x, y, z, rot_deg, mirrored):
    """Bring a STEP/IGES model in at (x, y, z) rotated rot_deg about Z.

    Each file is read ONCE. In the GUI the first instance is imported
    with ImportGui (so the model's own colours survive) into an
    App::Part named `name`; every further instance of the same file is
    an App::Link to that part -- re-importing the STEP per instance was
    what made a GUI run of a populated board take minutes. Headless (or
    mirrored) instances are plain Part::Features sharing one read."""
    _progress("placing %s" % name)
    P = App.Placement(V(x, y, z), App.Rotation(V(0, 0, 1), rot_deg))
    base = _model_shape(path)
    probe = base.copy()
    probe.Placement = P
    if _GUI and not mirrored:
        try:
            tpl = _MODEL_TEMPLATES.get(path)
            if tpl is not None:
                link = _doc.addObject("App::Link", name)
                link.setLink(tpl)
                link.Placement = P
                _PROBE.extend(_parts(probe))
                return link
            import ImportGui
            before = set(o.Name for o in _doc.Objects)
            ImportGui.insert(path, _doc.Name)
            new = [o for o in _doc.Objects if o.Name not in before]
            if new:
                part = _doc.addObject("App::Part", name)
                for o in [o for o in new if not any(p in new for p in o.InList)]:
                    part.addObject(o)
                part.Placement = P
                _MODEL_TEMPLATES[path] = part
                _PROBE.extend(_parts(probe))
                return part
        except Exception as e:
            App.Console.PrintWarning("HLayout: coloured import of %s failed (%s), "
                                     "reading plain shape\n" % (path, e))
    sh = base.copy()
    if mirrored:
        sh = sh.mirror(V(0, 0, 0), V(1, 0, 0))
    o = _doc.addObject("Part::Feature", name)
    o.Shape = sh
    o.Placement = P
    _PROBE.extend(_parts(o.Shape))
    return o


def _bondwire(p0, apex, p1, radius):
    """A swept loop p0 -> apex -> p1; falls back to a thin box path."""
    try:
        c = Part.BSplineCurve()
        c.interpolate([p0, apex, p1])
        spine = Part.Wire(c.toShape())
        prof = Part.Wire(Part.makeCircle(radius, p0, apex.sub(p0)))
        return spine.makePipeShell([prof], True, True)
    except Exception:
        legs = []
        for a, b in ((p0, apex), (apex, p1)):
            d = b.sub(a)
            L = d.Length
            if L > 1e-6:
                legs.append(Part.makeCylinder(radius, L, a, d))
        legs.append(Part.makeSphere(radius, apex))
        return _fuse(legs)


# --- layer 3 (1st Routing Conductor) : z 0.0000..0.0120 mm ---
_s = []
_s.append(Part.Face([_poly([V(9.82000,-19.85000,0.00000),V(9.22000,-19.85000,0.00000),V(9.22000,-19.55000,0.00000),V(9.82000,-19.55000,0.00000),V(9.82000,-19.85000,0.00000)])]).extrude(V(0,0,0.01200)))
_s.append(Part.Face([_poly([V(12.29500,-18.25000,0.00000),V(9.97000,-18.25000,0.00000),V(9.97000,-17.45000,0.00000),V(12.47000,-17.45000,0.00000),V(12.47000,-18.07725,0.00000),V(12.47426,-18.07788,0.00000),V(12.48854,-18.08146,0.00000),V(12.50240,-18.08642,0.00000),V(12.51571,-18.09271,0.00000),V(12.52834,-18.10028,0.00000),V(12.54016,-18.10905,0.00000),V(12.55107,-18.11893,0.00000),V(12.56095,-18.12984,0.00000),V(12.56972,-18.14166,0.00000),V(12.57729,-18.15429,0.00000),V(12.58358,-18.16760,0.00000),V(12.58854,-18.18146,0.00000),V(12.59212,-18.19574,0.00000),V(12.59428,-18.21030,0.00000),V(12.59500,-18.22500,0.00000),V(12.59500,-19.42500,0.00000),V(16.85500,-19.42500,0.00000),V(16.86970,-19.42572,0.00000),V(16.88426,-19.42788,0.00000),V(16.89854,-19.43146,0.00000),V(16.91240,-19.43642,0.00000),V(16.92571,-19.44271,0.00000),V(16.93834,-19.45028,0.00000),V(16.95016,-19.45905,0.00000),V(16.96107,-19.46893,0.00000),V(16.97095,-19.47984,0.00000),V(16.97972,-19.49166,0.00000),V(16.98729,-19.50429,0.00000),V(16.99358,-19.51760,0.00000),V(16.99854,-19.53146,0.00000),V(17.00212,-19.54574,0.00000),V(17.00275,-19.55000,0.00000),V(17.44000,-19.55000,0.00000),V(17.44000,-19.85000,0.00000),V(16.84000,-19.85000,0.00000),V(16.84000,-19.72500,0.00000),V(14.90000,-19.72500,0.00000),V(14.90000,-19.85000,0.00000),V(14.30000,-19.85000,0.00000),V(14.30000,-19.72500,0.00000),V(12.36000,-19.72500,0.00000),V(12.36000,-19.85000,0.00000),V(11.76000,-19.85000,0.00000),V(11.76000,-19.55000,0.00000),V(12.29500,-19.55000,0.00000),V(12.29500,-18.25000,0.00000)])]).extrude(V(0,0,0.01200)))
_s.append(Part.Face([_poly([V(19.98000,-19.85000,0.00000),V(19.38000,-19.85000,0.00000),V(19.38000,-19.55000,0.00000),V(19.98000,-19.55000,0.00000),V(19.98000,-19.85000,0.00000)])]).extrude(V(0,0,0.01200)))
_s.append(Part.Face([_poly([V(19.82000,-18.12700,0.00000),V(19.82000,-18.65000,0.00000),V(21.12000,-18.65000,0.00000),V(21.12000,-17.85000,0.00000),V(23.62000,-17.85000,0.00000),V(23.62000,-18.65000,0.00000),V(22.50000,-18.65000,0.00000),V(22.50000,-18.95000,0.00000),V(19.10000,-18.95000,0.00000),V(19.10000,-18.92700,0.00000),V(17.82000,-18.92700,0.00000),V(17.82000,-18.12700,0.00000),V(19.82000,-18.12700,0.00000)])]).extrude(V(0,0,0.01200)))
_s.append(Part.Face([_poly([V(19.35000,-15.57300,0.00000),V(19.35000,-14.25000,0.00000),V(23.75000,-14.25000,0.00000),V(23.75000,-13.40000,0.00000),V(23.47000,-13.40000,0.00000),V(23.47000,-12.50000,0.00000),V(25.47000,-12.50000,0.00000),V(25.47000,-13.40000,0.00000),V(24.05000,-13.40000,0.00000),V(24.05000,-14.55000,0.00000),V(19.65000,-14.55000,0.00000),V(19.65000,-15.57300,0.00000),V(19.82000,-15.57300,0.00000),V(19.82000,-16.37300,0.00000),V(17.82000,-16.37300,0.00000),V(17.82000,-15.57300,0.00000),V(19.35000,-15.57300,0.00000)])]).extrude(V(0,0,0.01200)))
_s.append(Part.Face([_poly([V(9.92760,-15.21358,0.00000),V(9.91429,-15.20729,0.00000),V(9.90166,-15.19972,0.00000),V(9.88984,-15.19095,0.00000),V(9.87893,-15.18107,0.00000),V(9.86905,-15.17016,0.00000),V(9.86028,-15.15834,0.00000),V(9.85271,-15.14571,0.00000),V(9.84642,-15.13240,0.00000),V(9.84146,-15.11854,0.00000),V(9.83788,-15.10426,0.00000),V(9.83572,-15.08970,0.00000),V(9.83500,-15.07500,0.00000),V(9.83500,-13.62700,0.00000),V(9.82000,-13.62700,0.00000),V(9.82000,-12.82700,0.00000),V(11.82000,-12.82700,0.00000),V(11.82000,-13.62700,0.00000),V(10.13500,-13.62700,0.00000),V(10.13500,-15.05000,0.00000),V(12.47000,-15.05000,0.00000),V(12.47000,-15.85000,0.00000),V(9.97000,-15.85000,0.00000),V(9.97000,-15.22423,0.00000),V(9.95574,-15.22212,0.00000),V(9.94146,-15.21854,0.00000),V(9.92760,-15.21358,0.00000)])]).extrude(V(0,0,0.01200)))
_s.append(Part.Face([_poly([V(17.32984,-13.69095,0.00000),V(17.31893,-13.68107,0.00000),V(17.30905,-13.67016,0.00000),V(17.30028,-13.65834,0.00000),V(17.29271,-13.64571,0.00000),V(17.28642,-13.63240,0.00000),V(17.28146,-13.61854,0.00000),V(17.27788,-13.60426,0.00000),V(17.27725,-13.60000,0.00000),V(16.64000,-13.60000,0.00000),V(16.64000,-11.60000,0.00000),V(17.44000,-11.60000,0.00000),V(17.44000,-13.42500,0.00000),V(18.25000,-13.42500,0.00000),V(18.25000,-11.60000,0.00000),V(18.62500,-11.60000,0.00000),V(18.62500,-10.57500,0.00000),V(18.62572,-10.56030,0.00000),V(18.62788,-10.54574,0.00000),V(18.63146,-10.53146,0.00000),V(18.63642,-10.51760,0.00000),V(18.64271,-10.50429,0.00000),V(18.65028,-10.49166,0.00000),V(18.65905,-10.47984,0.00000),V(18.66893,-10.46893,0.00000),V(18.67984,-10.45905,0.00000),V(18.69166,-10.45028,0.00000),V(18.70429,-10.44271,0.00000),V(18.71760,-10.43642,0.00000),V(18.73146,-10.43146,0.00000),V(18.74574,-10.42788,0.00000),V(18.76030,-10.42572,0.00000),V(18.77000,-10.42525,0.00000),V(18.77000,-9.52475,0.00000),V(18.76030,-9.52428,0.00000),V(18.74574,-9.52212,0.00000),V(18.73146,-9.51854,0.00000),V(18.71760,-9.51358,0.00000),V(18.70429,-9.50729,0.00000),V(18.69166,-9.49972,0.00000),V(18.67984,-9.49095,0.00000),V(18.66893,-9.48107,0.00000),V(18.65905,-9.47016,0.00000),V(18.65028,-9.45834,0.00000),V(18.64271,-9.44571,0.00000),V(18.63642,-9.43240,0.00000),V(18.63146,-9.41854,0.00000),V(18.62788,-9.40426,0.00000),V(18.62572,-9.38970,0.00000),V(18.62500,-9.37500,0.00000),V(18.62500,-8.45000,0.00000),V(17.92000,-8.45000,0.00000),V(17.92000,-8.23500,0.00000),V(16.16500,-8.23500,0.00000),V(16.15030,-8.23428,0.00000),V(16.13574,-8.23212,0.00000),V(16.12146,-8.22854,0.00000),V(16.10760,-8.22358,0.00000),V(16.09429,-8.21729,0.00000),V(16.08166,-8.20972,0.00000),V(16.06984,-8.20095,0.00000),V(16.05893,-8.19107,0.00000),V(16.04905,-8.18016,0.00000),V(16.04028,-8.16834,0.00000),V(16.03271,-8.15571,0.00000),V(16.02642,-8.14240,0.00000),V(16.02146,-8.12854,0.00000),V(16.01788,-8.11426,0.00000),V(16.01577,-8.10000,0.00000),V(13.82423,-8.10000,0.00000),V(13.82212,-8.11426,0.00000),V(13.81854,-8.12854,0.00000),V(13.81358,-8.14240,0.00000),V(13.80729,-8.15571,0.00000),V(13.79972,-8.16834,0.00000),V(13.79095,-8.18016,0.00000),V(13.78107,-8.19107,0.00000),V(13.77016,-8.20095,0.00000),V(13.75834,-8.20972,0.00000),V(13.74571,-8.21729,0.00000),V(13.73240,-8.22358,0.00000),V(13.71854,-8.22854,0.00000),V(13.70426,-8.23212,0.00000),V(13.68970,-8.23428,0.00000),V(13.67500,-8.23500,0.00000),V(12.56500,-8.23500,0.00000),V(12.55030,-8.23428,0.00000),V(12.53574,-8.23212,0.00000),V(12.52146,-8.22854,0.00000),V(12.50760,-8.22358,0.00000),V(12.49429,-8.21729,0.00000),V(12.48166,-8.20972,0.00000),V(12.46984,-8.20095,0.00000),V(12.45893,-8.19107,0.00000),V(12.44905,-8.18016,0.00000),V(12.44028,-8.16834,0.00000),V(12.43271,-8.15571,0.00000),V(12.43001,-8.15000,0.00000),V(10.07000,-8.15000,0.00000),V(10.07000,-7.35000,0.00000),V(12.57000,-7.35000,0.00000),V(12.57000,-7.93500,0.00000),V(13.67000,-7.93500,0.00000),V(13.67000,-7.30000,0.00000),V(16.17000,-7.30000,0.00000),V(16.17000,-7.93500,0.00000),V(17.92000,-7.93500,0.00000),V(17.92000,-7.65000,0.00000),V(20.42000,-7.65000,0.00000),V(20.42000,-8.45000,0.00000),V(18.92500,-8.45000,0.00000),V(18.92500,-9.35000,0.00000),V(19.47000,-9.35000,0.00000),V(19.47000,-10.60000,0.00000),V(18.92500,-10.60000,0.00000),V(18.92500,-11.60000,0.00000),V(19.05000,-11.60000,0.00000),V(19.05000,-13.60000,0.00000),V(18.41275,-13.60000,0.00000),V(18.41212,-13.60426,0.00000),V(18.40854,-13.61854,0.00000),V(18.40358,-13.63240,0.00000),V(18.39729,-13.64571,0.00000),V(18.38972,-13.65834,0.00000),V(18.38095,-13.67016,0.00000),V(18.37107,-13.68107,0.00000),V(18.36016,-13.69095,0.00000),V(18.34834,-13.69972,0.00000),V(18.33571,-13.70729,0.00000),V(18.32240,-13.71358,0.00000),V(18.30854,-13.71854,0.00000),V(18.29426,-13.72212,0.00000),V(18.27970,-13.72428,0.00000),V(18.26500,-13.72500,0.00000),V(17.42500,-13.72500,0.00000),V(17.41030,-13.72428,0.00000),V(17.39574,-13.72212,0.00000),V(17.38146,-13.71854,0.00000),V(17.36760,-13.71358,0.00000),V(17.35429,-13.70729,0.00000),V(17.34166,-13.69972,0.00000),V(17.32984,-13.69095,0.00000)])]).extrude(V(0,0,0.01200)))
_s.append(Part.Face([_poly([V(13.60000,-11.60000,0.00000),V(14.40000,-11.60000,0.00000),V(14.40000,-13.60000,0.00000),V(13.60000,-13.60000,0.00000),V(13.60000,-11.60000,0.00000)])]).extrude(V(0,0,0.01200)))
_s.append(Part.Face([_poly([V(9.82000,-11.07300,0.00000),V(9.82000,-10.27300,0.00000),V(11.82000,-10.27300,0.00000),V(11.82000,-11.07300,0.00000),V(9.82000,-11.07300,0.00000)])]).extrude(V(0,0,0.01200)))
_s.append(Part.Face([_poly([V(17.92000,-6.05000,0.00000),V(17.92000,-5.25000,0.00000),V(20.42000,-5.25000,0.00000),V(20.42000,-6.05000,0.00000),V(17.92000,-6.05000,0.00000)])]).extrude(V(0,0,0.01200)))
_s.append(Part.Face([_poly([V(14.90000,-3.45000,0.00000),V(14.90000,-3.58500,0.00000),V(16.84000,-3.58500,0.00000),V(16.84000,-3.45000,0.00000),V(17.44000,-3.45000,0.00000),V(17.44000,-3.58500,0.00000),V(19.38000,-3.58500,0.00000),V(19.38000,-3.45000,0.00000),V(19.98000,-3.45000,0.00000),V(19.98000,-3.75000,0.00000),V(19.55423,-3.75000,0.00000),V(19.55212,-3.76426,0.00000),V(19.54854,-3.77854,0.00000),V(19.54358,-3.79240,0.00000),V(19.53729,-3.80571,0.00000),V(19.52972,-3.81834,0.00000),V(19.52095,-3.83016,0.00000),V(19.51107,-3.84107,0.00000),V(19.50016,-3.85095,0.00000),V(19.48834,-3.85972,0.00000),V(19.47571,-3.86729,0.00000),V(19.46240,-3.87358,0.00000),V(19.44854,-3.87854,0.00000),V(19.43426,-3.88212,0.00000),V(19.41970,-3.88428,0.00000),V(19.40500,-3.88500,0.00000),V(12.71500,-3.88500,0.00000),V(12.71500,-4.96500,0.00000),V(12.71428,-4.97970,0.00000),V(12.71212,-4.99426,0.00000),V(12.70854,-5.00854,0.00000),V(12.70358,-5.02240,0.00000),V(12.69729,-5.03571,0.00000),V(12.68972,-5.04834,0.00000),V(12.68095,-5.06016,0.00000),V(12.67107,-5.07107,0.00000),V(12.66016,-5.08095,0.00000),V(12.64834,-5.08972,0.00000),V(12.63571,-5.09729,0.00000),V(12.62240,-5.10358,0.00000),V(12.60854,-5.10854,0.00000),V(12.59426,-5.11212,0.00000),V(12.57970,-5.11428,0.00000),V(12.57000,-5.11475,0.00000),V(12.57000,-5.75000,0.00000),V(10.07000,-5.75000,0.00000),V(10.07000,-4.95000,0.00000),V(12.41500,-4.95000,0.00000),V(12.41500,-3.58500,0.00000),V(14.30000,-3.58500,0.00000),V(14.30000,-3.45000,0.00000),V(14.90000,-3.45000,0.00000)])]).extrude(V(0,0,0.01200)))
_s.append(Part.Face([_poly([V(16.17000,-4.90000,0.00000),V(16.17000,-5.70000,0.00000),V(13.67000,-5.70000,0.00000),V(13.67000,-4.90000,0.00000),V(16.17000,-4.90000,0.00000)])]).extrude(V(0,0,0.01200)))
_s.append(Part.Face([_poly([V(9.82000,-3.75000,0.00000),V(9.22000,-3.75000,0.00000),V(9.22000,-3.45000,0.00000),V(9.82000,-3.45000,0.00000),V(9.82000,-3.75000,0.00000)])]).extrude(V(0,0,0.01200)))
_s.append(Part.Face([_poly([V(12.36000,-3.75000,0.00000),V(11.76000,-3.75000,0.00000),V(11.76000,-3.45000,0.00000),V(12.36000,-3.45000,0.00000),V(12.36000,-3.75000,0.00000)])]).extrude(V(0,0,0.01200)))
_s.append(Part.Face([_poly([V(27.60000,-19.85000,0.00000),V(27.00000,-19.85000,0.00000),V(27.00000,-19.55000,0.00000),V(27.60000,-19.55000,0.00000),V(27.60000,-19.85000,0.00000)])]).extrude(V(0,0,0.01200)))
_s.append(Part.Face([_poly([V(22.52000,-19.85000,0.00000),V(21.92000,-19.85000,0.00000),V(21.92000,-19.55000,0.00000),V(22.52000,-19.55000,0.00000),V(22.52000,-19.85000,0.00000)])]).extrude(V(0,0,0.01200)))
_s.append(Part.Face([_poly([V(24.89788,-19.54574,0.00000),V(24.90146,-19.53146,0.00000),V(24.90642,-19.51760,0.00000),V(24.91271,-19.50429,0.00000),V(24.92028,-19.49166,0.00000),V(24.92905,-19.47984,0.00000),V(24.93893,-19.46893,0.00000),V(24.94984,-19.45905,0.00000),V(24.96166,-19.45028,0.00000),V(24.97429,-19.44271,0.00000),V(24.98760,-19.43642,0.00000),V(25.00146,-19.43146,0.00000),V(25.01574,-19.42788,0.00000),V(25.03030,-19.42572,0.00000),V(25.04500,-19.42500,0.00000),V(25.79500,-19.42500,0.00000),V(25.79500,-17.92500,0.00000),V(25.79572,-17.91030,0.00000),V(25.79788,-17.89574,0.00000),V(25.80146,-17.88146,0.00000),V(25.80642,-17.86760,0.00000),V(25.81271,-17.85429,0.00000),V(25.82028,-17.84166,0.00000),V(25.82905,-17.82984,0.00000),V(25.83893,-17.81893,0.00000),V(25.84984,-17.80905,0.00000),V(25.86166,-17.80028,0.00000),V(25.87429,-17.79271,0.00000),V(25.88760,-17.78642,0.00000),V(25.90146,-17.78146,0.00000),V(25.91574,-17.77788,0.00000),V(25.92000,-17.77725,0.00000),V(25.92000,-15.45000,0.00000),V(26.72000,-15.45000,0.00000),V(26.72000,-17.95000,0.00000),V(26.09500,-17.95000,0.00000),V(26.09500,-19.72500,0.00000),V(25.06000,-19.72500,0.00000),V(25.06000,-19.85000,0.00000),V(24.46000,-19.85000,0.00000),V(24.46000,-19.55000,0.00000),V(24.89725,-19.55000,0.00000),V(24.89788,-19.54574,0.00000)])]).extrude(V(0,0,0.01200)))
_s.append(Part.Face([_poly([V(30.14000,-19.85000,0.00000),V(29.54000,-19.85000,0.00000),V(29.54000,-19.55000,0.00000),V(30.14000,-19.55000,0.00000),V(30.14000,-19.85000,0.00000)])]).extrude(V(0,0,0.01200)))
_s.append(Part.Face([_poly([V(28.94500,-18.28500,0.00000),V(28.94500,-17.95000,0.00000),V(28.32000,-17.95000,0.00000),V(28.32000,-15.45000,0.00000),V(29.12000,-15.45000,0.00000),V(29.12000,-17.77725,0.00000),V(29.12426,-17.77788,0.00000),V(29.13854,-17.78146,0.00000),V(29.15240,-17.78642,0.00000),V(29.16571,-17.79271,0.00000),V(29.17834,-17.80028,0.00000),V(29.19016,-17.80905,0.00000),V(29.20107,-17.81893,0.00000),V(29.21095,-17.82984,0.00000),V(29.21972,-17.84166,0.00000),V(29.22729,-17.85429,0.00000),V(29.23358,-17.86760,0.00000),V(29.23854,-17.88146,0.00000),V(29.24212,-17.89574,0.00000),V(29.24428,-17.91030,0.00000),V(29.24500,-17.92500,0.00000),V(29.24500,-17.98500,0.00000),V(31.02000,-17.98500,0.00000),V(31.02000,-17.92700,0.00000),V(33.02000,-17.92700,0.00000),V(33.02000,-18.72700,0.00000),V(31.02000,-18.72700,0.00000),V(31.02000,-18.28500,0.00000),V(28.94500,-18.28500,0.00000)])]).extrude(V(0,0,0.01200)))
_s.append(Part.Face([_poly([V(26.55000,-14.35000,0.00000),V(26.55000,-12.02500,0.00000),V(26.50000,-12.02500,0.00000),V(26.50000,-11.77500,0.00000),V(26.90000,-11.77500,0.00000),V(26.90000,-12.02500,0.00000),V(26.85000,-12.02500,0.00000),V(26.85000,-14.65000,0.00000),V(24.95000,-14.65000,0.00000),V(24.95000,-15.85000,0.00000),V(23.62000,-15.85000,0.00000),V(23.62000,-16.25000,0.00000),V(21.12000,-16.25000,0.00000),V(21.12000,-15.45000,0.00000),V(23.62000,-15.45000,0.00000),V(23.62000,-15.55000,0.00000),V(24.65000,-15.55000,0.00000),V(24.65000,-14.35000,0.00000),V(26.55000,-14.35000,0.00000)])]).extrude(V(0,0,0.01200)))
_s.append(Part.Face([_poly([V(22.09000,-11.60000,0.00000),V(22.09000,-13.60000,0.00000),V(21.29000,-13.60000,0.00000),V(21.29000,-11.60000,0.00000),V(22.09000,-11.60000,0.00000)])]).extrude(V(0,0,0.01200)))
_s.append(Part.Face([_poly([V(28.22000,-9.75000,0.00000),V(30.82000,-9.75000,0.00000),V(30.82000,-13.35000,0.00000),V(28.22000,-13.35000,0.00000),V(28.22000,-9.75000,0.00000)])]).extrude(V(0,0,0.01200)))
_s.append(Part.Face([_poly([V(27.20000,-11.32500,0.00000),V(26.80000,-11.32500,0.00000),V(26.80000,-11.07500,0.00000),V(27.20000,-11.07500,0.00000),V(27.20000,-11.32500,0.00000)])]).extrude(V(0,0,0.01200)))
_s.append(Part.Face([_poly([V(20.69760,-10.65358,0.00000),V(20.68429,-10.64729,0.00000),V(20.67166,-10.63972,0.00000),V(20.65984,-10.63095,0.00000),V(20.64893,-10.62107,0.00000),V(20.63905,-10.61016,0.00000),V(20.63151,-10.60000,0.00000),V(20.07000,-10.60000,0.00000),V(20.07000,-9.35000,0.00000),V(20.60725,-9.35000,0.00000),V(20.60788,-9.34574,0.00000),V(20.61146,-9.33146,0.00000),V(20.61642,-9.31760,0.00000),V(20.62271,-9.30429,0.00000),V(20.63028,-9.29166,0.00000),V(20.63905,-9.27984,0.00000),V(20.64893,-9.26893,0.00000),V(20.65984,-9.25905,0.00000),V(20.67166,-9.25028,0.00000),V(20.68429,-9.24271,0.00000),V(20.69760,-9.23642,0.00000),V(20.71146,-9.23146,0.00000),V(20.72574,-9.22788,0.00000),V(20.74030,-9.22572,0.00000),V(20.75500,-9.22500,0.00000),V(21.59500,-9.22500,0.00000),V(21.59500,-3.58500,0.00000),V(21.92000,-3.58500,0.00000),V(21.92000,-3.45000,0.00000),V(22.52000,-3.45000,0.00000),V(22.52000,-3.75000,0.00000),V(22.07423,-3.75000,0.00000),V(22.07212,-3.76426,0.00000),V(22.06854,-3.77854,0.00000),V(22.06358,-3.79240,0.00000),V(22.05729,-3.80571,0.00000),V(22.04972,-3.81834,0.00000),V(22.04095,-3.83016,0.00000),V(22.03107,-3.84107,0.00000),V(22.02016,-3.85095,0.00000),V(22.00834,-3.85972,0.00000),V(21.99571,-3.86729,0.00000),V(21.98240,-3.87358,0.00000),V(21.96854,-3.87854,0.00000),V(21.95426,-3.88212,0.00000),V(21.93970,-3.88428,0.00000),V(21.92500,-3.88500,0.00000),V(21.89500,-3.88500,0.00000),V(21.89500,-9.52500,0.00000),V(20.77000,-9.52500,0.00000),V(20.77000,-10.36500,0.00000),V(23.47000,-10.36500,0.00000),V(23.47000,-9.80000,0.00000),V(25.47000,-9.80000,0.00000),V(25.47000,-10.70000,0.00000),V(23.47000,-10.70000,0.00000),V(23.47000,-10.66500,0.00000),V(20.75500,-10.66500,0.00000),V(20.74030,-10.66428,0.00000),V(20.72574,-10.66212,0.00000),V(20.71146,-10.65854,0.00000),V(20.69760,-10.65358,0.00000)])]).extrude(V(0,0,0.01200)))
_s.append(Part.Face([_poly([V(27.10000,-10.62500,0.00000),V(26.70000,-10.62500,0.00000),V(26.70000,-10.37500,0.00000),V(27.10000,-10.37500,0.00000),V(27.10000,-10.62500,0.00000)])]).extrude(V(0,0,0.01200)))
_s.append(Part.Face([_poly([V(26.97000,-8.38300,0.00000),V(26.97000,-9.18300,0.00000),V(24.97000,-9.18300,0.00000),V(24.97000,-8.38300,0.00000),V(26.97000,-8.38300,0.00000)])]).extrude(V(0,0,0.01200)))
_s.append(Part.Face([_poly([V(22.27000,-8.00000,0.00000),V(22.27000,-7.30000,0.00000),V(23.52000,-7.30000,0.00000),V(23.52000,-8.00000,0.00000),V(22.27000,-8.00000,0.00000)])]).extrude(V(0,0,0.01200)))
_s.append(Part.Face([_poly([V(28.91000,-7.70000,0.00000),V(28.11000,-7.70000,0.00000),V(28.11000,-5.70000,0.00000),V(28.91000,-5.70000,0.00000),V(28.91000,-7.70000,0.00000)])]).extrude(V(0,0,0.01200)))
_s.append(Part.Face([_poly([V(30.83000,-7.70000,0.00000),V(30.03000,-7.70000,0.00000),V(30.03000,-5.70000,0.00000),V(30.83000,-5.70000,0.00000),V(30.83000,-7.70000,0.00000)])]).extrude(V(0,0,0.01200)))
_s.append(Part.Face([_poly([V(31.52500,-4.99500,0.00000),V(31.52500,-6.70500,0.00000),V(33.97000,-6.70500,0.00000),V(33.97000,-6.66100,0.00000),V(35.97000,-6.66100,0.00000),V(35.97000,-6.70500,0.00000),V(37.22500,-6.70500,0.00000),V(37.22500,-6.67500,0.00000),V(37.22572,-6.66030,0.00000),V(37.22788,-6.64574,0.00000),V(37.23146,-6.63146,0.00000),V(37.23642,-6.61760,0.00000),V(37.24271,-6.60429,0.00000),V(37.25028,-6.59166,0.00000),V(37.25905,-6.57984,0.00000),V(37.26893,-6.56893,0.00000),V(37.27984,-6.55905,0.00000),V(37.29166,-6.55028,0.00000),V(37.30429,-6.54271,0.00000),V(37.31760,-6.53642,0.00000),V(37.33146,-6.53146,0.00000),V(37.34574,-6.52788,0.00000),V(37.36030,-6.52572,0.00000),V(37.37000,-6.52525,0.00000),V(37.37000,-6.00000,0.00000),V(38.62000,-6.00000,0.00000),V(38.62000,-6.70000,0.00000),V(37.52500,-6.70000,0.00000),V(37.52500,-7.00500,0.00000),V(35.97000,-7.00500,0.00000),V(35.97000,-7.30525,0.00000),V(35.97970,-7.30572,0.00000),V(35.99426,-7.30788,0.00000),V(36.00854,-7.31146,0.00000),V(36.02240,-7.31642,0.00000),V(36.03571,-7.32271,0.00000),V(36.04834,-7.33028,0.00000),V(36.06016,-7.33905,0.00000),V(36.07107,-7.34893,0.00000),V(36.08095,-7.35984,0.00000),V(36.08972,-7.37166,0.00000),V(36.09729,-7.38429,0.00000),V(36.10358,-7.39760,0.00000),V(36.10854,-7.41146,0.00000),V(36.11212,-7.42574,0.00000),V(36.11428,-7.44030,0.00000),V(36.11500,-7.45500,0.00000),V(36.11500,-7.93522,0.00000),V(36.12016,-7.93905,0.00000),V(36.13107,-7.94893,0.00000),V(36.14095,-7.95984,0.00000),V(36.14972,-7.97166,0.00000),V(36.15729,-7.98429,0.00000),V(36.16358,-7.99760,0.00000),V(36.16854,-8.01146,0.00000),V(36.17212,-8.02574,0.00000),V(36.17428,-8.04030,0.00000),V(36.17475,-8.05000,0.00000),V(37.02000,-8.05000,0.00000),V(37.02000,-9.05000,0.00000),V(36.02000,-9.05000,0.00000),V(36.02000,-8.20500,0.00000),V(35.81500,-8.20500,0.00000),V(35.81500,-7.46100,0.00000),V(33.97000,-7.46100,0.00000),V(33.97000,-7.00500,0.00000),V(31.22500,-7.00500,0.00000),V(31.22500,-5.29500,0.00000),V(23.66500,-5.29500,0.00000),V(23.66500,-6.01500,0.00000),V(23.66428,-6.02970,0.00000),V(23.66212,-6.04426,0.00000),V(23.65854,-6.05854,0.00000),V(23.65358,-6.07240,0.00000),V(23.64729,-6.08571,0.00000),V(23.63972,-6.09834,0.00000),V(23.63095,-6.11016,0.00000),V(23.62107,-6.12107,0.00000),V(23.61016,-6.13095,0.00000),V(23.59834,-6.13972,0.00000),V(23.58571,-6.14729,0.00000),V(23.57240,-6.15358,0.00000),V(23.55854,-6.15854,0.00000),V(23.54426,-6.16212,0.00000),V(23.52970,-6.16428,0.00000),V(23.52000,-6.16475,0.00000),V(23.52000,-6.70000,0.00000),V(22.27000,-6.70000,0.00000),V(22.27000,-6.00000,0.00000),V(23.36500,-6.00000,0.00000),V(23.36500,-4.99500,0.00000),V(31.52500,-4.99500,0.00000)])]).extrude(V(0,0,0.01200)))
_s.append(Part.Face([_poly([V(26.97000,-5.71700,0.00000),V(26.97000,-6.51700,0.00000),V(24.97000,-6.51700,0.00000),V(24.97000,-5.71700,0.00000),V(26.97000,-5.71700,0.00000)])]).extrude(V(0,0,0.01200)))
_s.append(Part.Face([_poly([V(27.00000,-3.75000,0.00000),V(27.00000,-3.45000,0.00000),V(27.60000,-3.45000,0.00000),V(27.60000,-3.75000,0.00000),V(27.00000,-3.75000,0.00000)])]).extrude(V(0,0,0.01200)))
_s.append(Part.Face([_poly([V(29.54000,-3.75000,0.00000),V(29.54000,-3.45000,0.00000),V(30.14000,-3.45000,0.00000),V(30.14000,-3.75000,0.00000),V(29.54000,-3.75000,0.00000)])]).extrude(V(0,0,0.01200)))
_s.append(Part.Face([_poly([V(25.06000,-3.75000,0.00000),V(24.46000,-3.75000,0.00000),V(24.46000,-3.45000,0.00000),V(25.06000,-3.45000,0.00000),V(25.06000,-3.75000,0.00000)])]).extrude(V(0,0,0.01200)))
_s.append(Part.Face([_poly([V(35.22000,-19.85000,0.00000),V(34.62000,-19.85000,0.00000),V(34.62000,-19.55000,0.00000),V(35.22000,-19.55000,0.00000),V(35.22000,-19.85000,0.00000)])]).extrude(V(0,0,0.01200)))
_s.append(Part.Face([_poly([V(37.76000,-19.85000,0.00000),V(37.16000,-19.85000,0.00000),V(37.16000,-19.55000,0.00000),V(37.76000,-19.55000,0.00000),V(37.76000,-19.85000,0.00000)])]).extrude(V(0,0,0.01200)))
_s.append(Part.Face([_poly([V(32.68000,-19.85000,0.00000),V(32.08000,-19.85000,0.00000),V(32.08000,-19.55000,0.00000),V(32.68000,-19.55000,0.00000),V(32.68000,-19.85000,0.00000)])]).extrude(V(0,0,0.01200)))
_s.append(Part.Face([_poly([V(37.34700,-17.60000,0.00000),V(36.54700,-17.60000,0.00000),V(36.54700,-15.60000,0.00000),V(37.34700,-15.60000,0.00000),V(37.34700,-17.60000,0.00000)])]).extrude(V(0,0,0.01200)))
_s.append(Part.Face([_poly([V(34.79300,-17.60000,0.00000),V(33.99300,-17.60000,0.00000),V(33.99300,-15.60000,0.00000),V(34.79300,-15.60000,0.00000),V(34.79300,-17.60000,0.00000)])]).extrude(V(0,0,0.01200)))
_s.append(Part.Face([_poly([V(39.77000,-15.80000,0.00000),V(39.77000,-16.50000,0.00000),V(38.52000,-16.50000,0.00000),V(38.52000,-15.80000,0.00000),V(39.77000,-15.80000,0.00000)])]).extrude(V(0,0,0.01200)))
_s.append(Part.Face([_poly([V(31.02000,-16.17300,0.00000),V(31.02000,-15.37300,0.00000),V(33.02000,-15.37300,0.00000),V(33.02000,-16.17300,0.00000),V(31.02000,-16.17300,0.00000)])]).extrude(V(0,0,0.01200)))
_s.append(Part.Face([_poly([V(38.71854,-14.51854,0.00000),V(38.71358,-14.53240,0.00000),V(38.70729,-14.54571,0.00000),V(38.69972,-14.55834,0.00000),V(38.69095,-14.57016,0.00000),V(38.68107,-14.58107,0.00000),V(38.67016,-14.59095,0.00000),V(38.65834,-14.59972,0.00000),V(38.64571,-14.60729,0.00000),V(38.63240,-14.61358,0.00000),V(38.61854,-14.61854,0.00000),V(38.60426,-14.62212,0.00000),V(38.58970,-14.62428,0.00000),V(38.57500,-14.62500,0.00000),V(36.40300,-14.62500,0.00000),V(36.40300,-14.85000,0.00000),V(35.60300,-14.85000,0.00000),V(35.60300,-12.85000,0.00000),V(36.40300,-12.85000,0.00000),V(36.40300,-14.32500,0.00000),V(38.57000,-14.32500,0.00000),V(38.57000,-13.80000,0.00000),V(39.82000,-13.80000,0.00000),V(39.82000,-14.50000,0.00000),V(38.72275,-14.50000,0.00000),V(38.72212,-14.50426,0.00000),V(38.71854,-14.51854,0.00000)])]).extrude(V(0,0,0.01200)))
_s.append(Part.Face([_poly([V(32.93700,-12.85000,0.00000),V(33.73700,-12.85000,0.00000),V(33.73700,-14.85000,0.00000),V(32.93700,-14.85000,0.00000),V(32.93700,-12.85000,0.00000)])]).extrude(V(0,0,0.01200)))
_s.append(Part.Face([_poly([V(32.00000,-13.22500,0.00000),V(31.60000,-13.22500,0.00000),V(31.60000,-12.97500,0.00000),V(32.00000,-12.97500,0.00000),V(32.00000,-13.22500,0.00000)])]).extrude(V(0,0,0.01200)))
_s.append(Part.Face([_poly([V(35.27000,-12.25000,0.00000),V(35.27000,-11.55000,0.00000),V(36.52000,-11.55000,0.00000),V(36.52000,-12.25000,0.00000),V(35.27000,-12.25000,0.00000)])]).extrude(V(0,0,0.01200)))
_s.append(Part.Face([_poly([V(33.06516,-11.76705,0.00000),V(33.07607,-11.77693,0.00000),V(33.08595,-11.78784,0.00000),V(33.09472,-11.79966,0.00000),V(33.10229,-11.81229,0.00000),V(33.10858,-11.82560,0.00000),V(33.11354,-11.83946,0.00000),V(33.11712,-11.85374,0.00000),V(33.11928,-11.86830,0.00000),V(33.12000,-11.88300,0.00000),V(33.11928,-11.89770,0.00000),V(33.11712,-11.91226,0.00000),V(33.11482,-11.92142,0.00000),V(33.11500,-11.92500,0.00000),V(33.11428,-11.93970,0.00000),V(33.11212,-11.95426,0.00000),V(33.10854,-11.96854,0.00000),V(33.10358,-11.98240,0.00000),V(33.09729,-11.99571,0.00000),V(33.08972,-12.00834,0.00000),V(33.08095,-12.02016,0.00000),V(33.07107,-12.03107,0.00000),V(33.06016,-12.04095,0.00000),V(33.04834,-12.04972,0.00000),V(33.03571,-12.05729,0.00000),V(33.02240,-12.06358,0.00000),V(33.00854,-12.06854,0.00000),V(32.99426,-12.07212,0.00000),V(32.97970,-12.07428,0.00000),V(32.96500,-12.07500,0.00000),V(31.18500,-12.07500,0.00000),V(31.18500,-9.55500,0.00000),V(38.30500,-9.55500,0.00000),V(38.30500,-9.75000,0.00000),V(38.94300,-9.75000,0.00000),V(38.94300,-11.75000,0.00000),V(38.14300,-11.75000,0.00000),V(38.14300,-9.91441,0.00000),V(38.14030,-9.91428,0.00000),V(38.12574,-9.91212,0.00000),V(38.11146,-9.90854,0.00000),V(38.09760,-9.90358,0.00000),V(38.08429,-9.89729,0.00000),V(38.07166,-9.88972,0.00000),V(38.05984,-9.88095,0.00000),V(38.04893,-9.87107,0.00000),V(38.03905,-9.86016,0.00000),V(38.03522,-9.85500,0.00000),V(31.48500,-9.85500,0.00000),V(31.48500,-11.75951,0.00000),V(31.48666,-11.75828,0.00000),V(31.49929,-11.75071,0.00000),V(31.51260,-11.74442,0.00000),V(31.52646,-11.73946,0.00000),V(31.54074,-11.73588,0.00000),V(31.55530,-11.73372,0.00000),V(31.57000,-11.73300,0.00000),V(32.97000,-11.73300,0.00000),V(32.98470,-11.73372,0.00000),V(32.99926,-11.73588,0.00000),V(33.01354,-11.73946,0.00000),V(33.02740,-11.74442,0.00000),V(33.04071,-11.75071,0.00000),V(33.05334,-11.75828,0.00000),V(33.06516,-11.76705,0.00000)])]).extrude(V(0,0,0.01200)))
_s.append(Part.Face([_poly([V(36.52000,-10.25000,0.00000),V(36.52000,-10.95000,0.00000),V(35.27000,-10.95000,0.00000),V(35.27000,-10.75000,0.00000),V(32.10000,-10.75000,0.00000),V(32.10000,-10.72500,0.00000),V(31.90000,-10.72500,0.00000),V(31.90000,-10.47500,0.00000),V(32.10000,-10.47500,0.00000),V(32.10000,-10.45000,0.00000),V(35.27000,-10.45000,0.00000),V(35.27000,-10.25000,0.00000),V(36.52000,-10.25000,0.00000)])]).extrude(V(0,0,0.01200)))
_s.append(Part.Face([_poly([V(37.74074,-8.40288,0.00000),V(37.75530,-8.40072,0.00000),V(37.77000,-8.40000,0.00000),V(38.99577,-8.40000,0.00000),V(38.99788,-8.38574,0.00000),V(39.00146,-8.37146,0.00000),V(39.00642,-8.35760,0.00000),V(39.01271,-8.34429,0.00000),V(39.02028,-8.33166,0.00000),V(39.02500,-8.32530,0.00000),V(39.02500,-5.32500,0.00000),V(38.62000,-5.32500,0.00000),V(38.62000,-5.40000,0.00000),V(37.37000,-5.40000,0.00000),V(37.37000,-4.70000,0.00000),V(38.62000,-4.70000,0.00000),V(38.62000,-5.02500,0.00000),V(39.02500,-5.02500,0.00000),V(39.02500,-3.58500,0.00000),V(39.70000,-3.58500,0.00000),V(39.70000,-3.45000,0.00000),V(40.30000,-3.45000,0.00000),V(40.30000,-3.58500,0.00000),V(42.24000,-3.58500,0.00000),V(42.24000,-3.45000,0.00000),V(42.84000,-3.45000,0.00000),V(42.84000,-3.58525,0.00000),V(42.84970,-3.58572,0.00000),V(42.86426,-3.58788,0.00000),V(42.87854,-3.59146,0.00000),V(42.89240,-3.59642,0.00000),V(42.90571,-3.60271,0.00000),V(42.91834,-3.61028,0.00000),V(42.93016,-3.61905,0.00000),V(42.94107,-3.62893,0.00000),V(42.95095,-3.63984,0.00000),V(42.95972,-3.65166,0.00000),V(42.96729,-3.66429,0.00000),V(42.97358,-3.67760,0.00000),V(42.97854,-3.69146,0.00000),V(42.98212,-3.70574,0.00000),V(42.98428,-3.72030,0.00000),V(42.98500,-3.73500,0.00000),V(42.98500,-5.05500,0.00000),V(43.04500,-5.05500,0.00000),V(43.05970,-5.05572,0.00000),V(43.07426,-5.05788,0.00000),V(43.08854,-5.06146,0.00000),V(43.10240,-5.06642,0.00000),V(43.11571,-5.07271,0.00000),V(43.12834,-5.08028,0.00000),V(43.14016,-5.08905,0.00000),V(43.15107,-5.09893,0.00000),V(43.16095,-5.10984,0.00000),V(43.16972,-5.12166,0.00000),V(43.17729,-5.13429,0.00000),V(43.18358,-5.14760,0.00000),V(43.18854,-5.16146,0.00000),V(43.19212,-5.17574,0.00000),V(43.19428,-5.19030,0.00000),V(43.19475,-5.20000,0.00000),V(44.27000,-5.20000,0.00000),V(44.27000,-5.90000,0.00000),V(43.02000,-5.90000,0.00000),V(43.02000,-5.35500,0.00000),V(42.68500,-5.35500,0.00000),V(42.68500,-3.75000,0.00000),V(42.41423,-3.75000,0.00000),V(42.41212,-3.76426,0.00000),V(42.40854,-3.77854,0.00000),V(42.40358,-3.79240,0.00000),V(42.39729,-3.80571,0.00000),V(42.38972,-3.81834,0.00000),V(42.38095,-3.83016,0.00000),V(42.37107,-3.84107,0.00000),V(42.36016,-3.85095,0.00000),V(42.34834,-3.85972,0.00000),V(42.33571,-3.86729,0.00000),V(42.32240,-3.87358,0.00000),V(42.30854,-3.87854,0.00000),V(42.29426,-3.88212,0.00000),V(42.27970,-3.88428,0.00000),V(42.26500,-3.88500,0.00000),V(39.32500,-3.88500,0.00000),V(39.32500,-5.02500,0.00000),V(39.32500,-5.17500,0.00000),V(39.32500,-8.56500,0.00000),V(39.31923,-8.56500,0.00000),V(39.31712,-8.57926,0.00000),V(39.31354,-8.59354,0.00000),V(39.30858,-8.60740,0.00000),V(39.30229,-8.62071,0.00000),V(39.29472,-8.63334,0.00000),V(39.28595,-8.64516,0.00000),V(39.27607,-8.65607,0.00000),V(39.26516,-8.66595,0.00000),V(39.25334,-8.67472,0.00000),V(39.24071,-8.68229,0.00000),V(39.22740,-8.68858,0.00000),V(39.21354,-8.69354,0.00000),V(39.19926,-8.69712,0.00000),V(39.18470,-8.69928,0.00000),V(39.17000,-8.70000,0.00000),V(37.77000,-8.70000,0.00000),V(37.75530,-8.69928,0.00000),V(37.74074,-8.69712,0.00000),V(37.72646,-8.69354,0.00000),V(37.71260,-8.68858,0.00000),V(37.69929,-8.68229,0.00000),V(37.68713,-8.67500,0.00000),V(37.57000,-8.67500,0.00000),V(37.57000,-8.42500,0.00000),V(37.68713,-8.42500,0.00000),V(37.69929,-8.41771,0.00000),V(37.71260,-8.41142,0.00000),V(37.72646,-8.40646,0.00000),V(37.74074,-8.40288,0.00000)])]).extrude(V(0,0,0.01200)))
_s.append(Part.Face([_poly([V(34.49572,-3.72030,0.00000),V(34.49788,-3.70574,0.00000),V(34.50146,-3.69146,0.00000),V(34.50642,-3.67760,0.00000),V(34.51271,-3.66429,0.00000),V(34.52028,-3.65166,0.00000),V(34.52905,-3.63984,0.00000),V(34.53893,-3.62893,0.00000),V(34.54984,-3.61905,0.00000),V(34.56166,-3.61028,0.00000),V(34.57429,-3.60271,0.00000),V(34.58760,-3.59642,0.00000),V(34.60146,-3.59146,0.00000),V(34.61574,-3.58788,0.00000),V(34.62000,-3.58725,0.00000),V(34.62000,-3.45000,0.00000),V(35.22000,-3.45000,0.00000),V(35.22000,-3.75000,0.00000),V(34.79500,-3.75000,0.00000),V(34.79500,-5.03900,0.00000),V(35.97000,-5.03900,0.00000),V(35.97000,-5.83900,0.00000),V(33.97000,-5.83900,0.00000),V(33.97000,-5.03900,0.00000),V(34.49500,-5.03900,0.00000),V(34.49500,-3.73500,0.00000),V(34.49572,-3.72030,0.00000)])]).extrude(V(0,0,0.01200)))
_s.append(Part.Face([_poly([V(32.08000,-3.75000,0.00000),V(32.08000,-3.45000,0.00000),V(32.68000,-3.45000,0.00000),V(32.68000,-3.75000,0.00000),V(32.08000,-3.75000,0.00000)])]).extrude(V(0,0,0.01200)))
_s.append(Part.Face([_poly([V(37.76000,-3.75000,0.00000),V(37.16000,-3.75000,0.00000),V(37.16000,-3.45000,0.00000),V(37.76000,-3.45000,0.00000),V(37.76000,-3.75000,0.00000)])]).extrude(V(0,0,0.01200)))
_s.append(Part.Face([_poly([V(40.30000,-19.85000,0.00000),V(39.70000,-19.85000,0.00000),V(39.70000,-19.55000,0.00000),V(40.30000,-19.55000,0.00000),V(40.30000,-19.85000,0.00000)])]).extrude(V(0,0,0.01200)))
_s.append(Part.Face([_poly([V(42.84000,-19.85000,0.00000),V(42.24000,-19.85000,0.00000),V(42.24000,-19.55000,0.00000),V(42.84000,-19.55000,0.00000),V(42.84000,-19.85000,0.00000)])]).extrude(V(0,0,0.01200)))
_s.append(Part.Face([_poly([V(45.38000,-19.85000,0.00000),V(44.78000,-19.85000,0.00000),V(44.78000,-19.55000,0.00000),V(45.38000,-19.55000,0.00000),V(45.38000,-19.85000,0.00000)])]).extrude(V(0,0,0.01200)))
_s.append(Part.Face([_poly([V(43.34972,-18.45834,0.00000),V(43.34095,-18.47016,0.00000),V(43.33107,-18.48107,0.00000),V(43.32016,-18.49095,0.00000),V(43.30834,-18.49972,0.00000),V(43.29571,-18.50729,0.00000),V(43.28240,-18.51358,0.00000),V(43.26854,-18.51854,0.00000),V(43.25426,-18.52212,0.00000),V(43.23970,-18.52428,0.00000),V(43.22500,-18.52500,0.00000),V(42.86500,-18.52500,0.00000),V(42.85030,-18.52428,0.00000),V(42.83574,-18.52212,0.00000),V(42.82146,-18.51854,0.00000),V(42.80760,-18.51358,0.00000),V(42.79429,-18.50729,0.00000),V(42.78166,-18.49972,0.00000),V(42.76984,-18.49095,0.00000),V(42.75893,-18.48107,0.00000),V(42.74905,-18.47016,0.00000),V(42.74028,-18.45834,0.00000),V(42.73271,-18.44571,0.00000),V(42.72642,-18.43240,0.00000),V(42.72146,-18.41854,0.00000),V(42.71932,-18.41000,0.00000),V(40.87000,-18.41000,0.00000),V(40.87000,-17.92500,0.00000),V(39.74500,-17.92500,0.00000),V(39.73030,-17.92428,0.00000),V(39.71574,-17.92212,0.00000),V(39.70146,-17.91854,0.00000),V(39.68760,-17.91358,0.00000),V(39.67429,-17.90729,0.00000),V(39.66166,-17.89972,0.00000),V(39.64984,-17.89095,0.00000),V(39.63893,-17.88107,0.00000),V(39.62905,-17.87016,0.00000),V(39.62028,-17.85834,0.00000),V(39.61271,-17.84571,0.00000),V(39.60642,-17.83240,0.00000),V(39.60146,-17.81854,0.00000),V(39.59788,-17.80426,0.00000),V(39.59725,-17.80000,0.00000),V(38.52000,-17.80000,0.00000),V(38.52000,-17.10000,0.00000),V(39.77000,-17.10000,0.00000),V(39.77000,-17.62500,0.00000),V(40.87000,-17.62500,0.00000),V(40.87000,-17.61000,0.00000),V(42.87000,-17.61000,0.00000),V(42.87000,-18.22500,0.00000),V(43.22000,-18.22500,0.00000),V(43.22000,-17.58300,0.00000),V(45.22000,-17.58300,0.00000),V(45.22000,-18.38300,0.00000),V(43.37461,-18.38300,0.00000),V(43.37428,-18.38970,0.00000),V(43.37212,-18.40426,0.00000),V(43.36854,-18.41854,0.00000),V(43.36358,-18.43240,0.00000),V(43.35729,-18.44571,0.00000),V(43.34972,-18.45834,0.00000)])]).extrude(V(0,0,0.01200)))
_s.append(Part.Face([_poly([V(40.37500,-15.85500,0.00000),V(40.37500,-13.09500,0.00000),V(39.82000,-13.09500,0.00000),V(39.82000,-13.20000,0.00000),V(38.57000,-13.20000,0.00000),V(38.57000,-12.50000,0.00000),V(39.82000,-12.50000,0.00000),V(39.82000,-12.79500,0.00000),V(40.52500,-12.79500,0.00000),V(41.07000,-12.79500,0.00000),V(41.07000,-12.45000,0.00000),V(42.32000,-12.45000,0.00000),V(42.32000,-13.15000,0.00000),V(41.07000,-13.15000,0.00000),V(41.07000,-13.09500,0.00000),V(40.67500,-13.09500,0.00000),V(40.67500,-15.55500,0.00000),V(40.88500,-15.55500,0.00000),V(40.89970,-15.55572,0.00000),V(40.91426,-15.55788,0.00000),V(40.92854,-15.56146,0.00000),V(40.94240,-15.56642,0.00000),V(40.95571,-15.57271,0.00000),V(40.96834,-15.58028,0.00000),V(40.98016,-15.58905,0.00000),V(40.99107,-15.59893,0.00000),V(41.00095,-15.60984,0.00000),V(41.00972,-15.62166,0.00000),V(41.01729,-15.63429,0.00000),V(41.02358,-15.64760,0.00000),V(41.02854,-15.66146,0.00000),V(41.03212,-15.67574,0.00000),V(41.03423,-15.69000,0.00000),V(42.87000,-15.69000,0.00000),V(42.87000,-16.49000,0.00000),V(40.87000,-16.49000,0.00000),V(40.87000,-15.85500,0.00000),V(40.37500,-15.85500,0.00000)])]).extrude(V(0,0,0.01200)))
_s.append(Part.Face([_poly([V(43.22000,-15.71700,0.00000),V(43.22000,-14.91700,0.00000),V(45.22000,-14.91700,0.00000),V(45.22000,-15.71700,0.00000),V(43.22000,-15.71700,0.00000)])]).extrude(V(0,0,0.01200)))
_s.append(Part.Face([_poly([V(42.32000,-13.75000,0.00000),V(42.32000,-14.45000,0.00000),V(41.07000,-14.45000,0.00000),V(41.07000,-13.75000,0.00000),V(42.32000,-13.75000,0.00000)])]).extrude(V(0,0,0.01200)))
_s.append(Part.Face([_poly([V(45.07000,-14.08300,0.00000),V(43.07000,-14.08300,0.00000),V(43.07000,-13.28300,0.00000),V(45.07000,-13.28300,0.00000),V(45.07000,-14.08300,0.00000)])]).extrude(V(0,0,0.01200)))
_s.append(Part.Face([_poly([V(45.07000,-10.61700,0.00000),V(45.07000,-11.41700,0.00000),V(43.07000,-11.41700,0.00000),V(43.07000,-10.61700,0.00000),V(45.07000,-10.61700,0.00000)])]).extrude(V(0,0,0.01200)))
_s.append(Part.Face([_poly([V(43.02000,-6.50000,0.00000),V(44.27000,-6.50000,0.00000),V(44.27000,-7.20000,0.00000),V(43.02000,-7.20000,0.00000),V(43.02000,-7.05000,0.00000),V(42.65000,-7.05000,0.00000),V(42.65000,-10.25000,0.00000),V(41.49700,-10.25000,0.00000),V(41.49700,-11.75000,0.00000),V(40.69700,-11.75000,0.00000),V(40.69700,-9.75000,0.00000),V(41.49700,-9.75000,0.00000),V(41.49700,-9.95000,0.00000),V(42.35000,-9.95000,0.00000),V(42.35000,-6.75000,0.00000),V(43.02000,-6.75000,0.00000),V(43.02000,-6.50000,0.00000)])]).extrude(V(0,0,0.01200)))
_s.append(Part.Face([_poly([V(44.52000,-9.25000,0.00000),V(44.52000,-9.30000,0.00000),V(44.80000,-9.30000,0.00000),V(44.80000,-10.60000,0.00000),V(43.20000,-10.60000,0.00000),V(43.20000,-9.30000,0.00000),V(43.27000,-9.30000,0.00000),V(43.27000,-9.25000,0.00000),V(44.52000,-9.25000,0.00000)])]).extrude(V(0,0,0.01200)))
_s.append(Part.Face([_poly([V(44.52000,-7.95000,0.00000),V(44.52000,-8.65000,0.00000),V(43.27000,-8.65000,0.00000),V(43.27000,-7.95000,0.00000),V(44.52000,-7.95000,0.00000)])]).extrude(V(0,0,0.01200)))
_s.append(Part.Face([_poly([V(41.97000,-7.16000,0.00000),V(41.97000,-7.96000,0.00000),V(39.97000,-7.96000,0.00000),V(39.97000,-7.16000,0.00000),V(41.97000,-7.16000,0.00000)])]).extrude(V(0,0,0.01200)))
_s.append(Part.Face([_poly([V(41.97000,-5.24000,0.00000),V(41.97000,-6.04000,0.00000),V(39.97000,-6.04000,0.00000),V(39.97000,-5.24000,0.00000),V(41.97000,-5.24000,0.00000)])]).extrude(V(0,0,0.01200)))
_s.append(Part.Face([_poly([V(44.78000,-3.75000,0.00000),V(44.78000,-3.45000,0.00000),V(45.38000,-3.45000,0.00000),V(45.38000,-3.75000,0.00000),V(44.78000,-3.75000,0.00000)])]).extrude(V(0,0,0.01200)))
_add('1st Routing Conductor' + '_L3', _fuse(_s), (1.0000,0.5020,0.2510), surface=True)
# --- layer 4 (Routing Dielectric) : z 0.0120..0.0420 mm ---
_s = []
_s.append(Part.Face([_poly([V(40.02000,-18.76000,0.01200),V(43.72000,-18.76000,0.01200),V(43.72000,-18.73300,0.01200),V(45.08000,-18.73300,0.01200),V(45.08000,-19.85000,0.01200),V(35.42500,-19.85000,0.01200),V(24.17500,-19.85000,0.01200),V(18.82000,-19.85000,0.01200),V(9.52000,-19.85000,0.01200),V(9.52000,-13.97700,0.01200),V(12.67000,-13.97700,0.01200),V(12.67000,-9.92300,0.01200),V(9.52000,-9.92300,0.01200),V(9.52000,-3.45000,0.01200),V(20.12500,-3.45000,0.01200),V(27.65000,-3.45000,0.01200),V(31.67500,-3.45000,0.01200),V(37.07500,-3.45000,0.01200),V(45.08000,-3.45000,0.01200),V(45.08000,-8.02500,0.01200),V(45.08000,-10.26700,0.01200),V(42.22000,-10.26700,0.01200),V(42.22000,-14.02500,0.01200),V(42.22000,-14.43300,0.01200),V(45.08000,-14.43300,0.01200),V(45.08000,-14.56700,0.01200),V(42.37000,-14.56700,0.01200),V(42.37000,-15.34000,0.01200),V(40.02000,-15.34000,0.01200),V(40.02000,-16.27500,0.01200),V(40.02000,-18.76000,0.01200)]), _poly([V(35.55000,-19.40000,0.01200),V(35.55000,-19.15000,0.01200),V(35.42500,-19.15000,0.01200),V(35.30000,-19.15000,0.01200),V(35.30000,-19.40000,0.01200),V(35.42500,-19.40000,0.01200),V(35.55000,-19.40000,0.01200)]), _poly([V(37.69700,-18.45000,0.01200),V(37.69700,-16.27500,0.01200),V(37.69700,-14.75000,0.01200),V(36.75300,-14.75000,0.01200),V(36.75300,-12.00000,0.01200),V(36.75000,-12.00000,0.01200),V(36.75000,-11.95000,0.01200),V(36.50000,-11.95000,0.01200),V(36.50000,-12.00000,0.01200),V(32.58700,-12.00000,0.01200),V(32.58700,-15.02300,0.01200),V(30.17000,-15.02300,0.01200),V(30.17000,-19.07700,0.01200),V(33.87000,-19.07700,0.01200),V(33.87000,-18.45000,0.01200),V(35.42500,-18.45000,0.01200),V(37.69700,-18.45000,0.01200)]), _poly([V(38.30000,-16.40000,0.01200),V(38.55000,-16.40000,0.01200),V(38.55000,-16.27500,0.01200),V(38.55000,-16.15000,0.01200),V(38.30000,-16.15000,0.01200),V(38.30000,-16.27500,0.01200),V(38.30000,-16.40000,0.01200)]), _poly([V(20.00000,-5.80000,0.01200),V(20.00000,-6.05000,0.01200),V(20.12500,-6.05000,0.01200),V(20.25000,-6.05000,0.01200),V(20.25000,-5.80000,0.01200),V(20.12500,-5.80000,0.01200),V(20.00000,-5.80000,0.01200)]), _poly([V(22.10000,-6.20000,0.01200),V(22.35000,-6.20000,0.01200),V(22.35000,-6.07500,0.01200),V(22.35000,-5.95000,0.01200),V(22.10000,-5.95000,0.01200),V(22.10000,-6.07500,0.01200),V(22.10000,-6.20000,0.01200)]), _poly([V(24.12000,-9.53300,0.01200),V(27.82000,-9.53300,0.01200),V(27.82000,-8.55000,0.01200),V(31.18000,-8.55000,0.01200),V(31.18000,-4.85000,0.01200),V(27.76000,-4.85000,0.01200),V(27.76000,-5.36700,0.01200),V(27.65000,-5.36700,0.01200),V(24.12000,-5.36700,0.01200),V(24.12000,-6.07500,0.01200),V(24.12000,-9.53300,0.01200)]), _poly([V(31.55000,-3.85000,0.01200),V(31.55000,-4.10000,0.01200),V(31.67500,-4.10000,0.01200),V(31.80000,-4.10000,0.01200),V(31.80000,-3.85000,0.01200),V(31.67500,-3.85000,0.01200),V(31.55000,-3.85000,0.01200)]), _poly([V(31.55000,-6.40000,0.01200),V(31.55000,-6.65000,0.01200),V(31.67500,-6.65000,0.01200),V(31.80000,-6.65000,0.01200),V(31.80000,-6.40000,0.01200),V(31.67500,-6.40000,0.01200),V(31.55000,-6.40000,0.01200)]), _poly([V(33.80000,-9.65000,0.01200),V(34.05000,-9.65000,0.01200),V(34.05000,-9.52500,0.01200),V(34.05000,-9.40000,0.01200),V(33.80000,-9.40000,0.01200),V(33.80000,-9.52500,0.01200),V(33.80000,-9.65000,0.01200)]), _poly([V(34.10000,-10.45000,0.01200),V(34.10000,-10.70000,0.01200),V(34.22500,-10.70000,0.01200),V(34.35000,-10.70000,0.01200),V(34.35000,-10.45000,0.01200),V(34.22500,-10.45000,0.01200),V(34.10000,-10.45000,0.01200)]), _poly([V(32.70000,-10.75000,0.01200),V(32.45000,-10.75000,0.01200),V(32.45000,-10.87500,0.01200),V(32.45000,-11.00000,0.01200),V(32.70000,-11.00000,0.01200),V(32.70000,-10.87500,0.01200),V(32.70000,-10.75000,0.01200)]), _poly([V(31.85000,-12.85000,0.01200),V(31.85000,-13.10000,0.01200),V(31.97500,-13.10000,0.01200),V(32.10000,-13.10000,0.01200),V(32.10000,-12.85000,0.01200),V(31.97500,-12.85000,0.01200),V(31.85000,-12.85000,0.01200)]), _poly([V(31.05000,-13.60000,0.01200),V(30.80000,-13.60000,0.01200),V(30.80000,-13.72500,0.01200),V(30.80000,-13.85000,0.01200),V(31.05000,-13.85000,0.01200),V(31.05000,-13.72500,0.01200),V(31.05000,-13.60000,0.01200)]), _poly([V(26.40000,-12.25000,0.01200),V(26.15000,-12.25000,0.01200),V(26.15000,-12.37500,0.01200),V(26.15000,-12.50000,0.01200),V(26.40000,-12.50000,0.01200),V(26.40000,-12.37500,0.01200),V(26.40000,-12.25000,0.01200)]), _poly([V(24.05000,-14.80000,0.01200),V(24.05000,-15.05000,0.01200),V(24.17500,-15.05000,0.01200),V(24.30000,-15.05000,0.01200),V(24.30000,-14.80000,0.01200),V(24.17500,-14.80000,0.01200),V(24.05000,-14.80000,0.01200)]), _poly([V(18.82000,-19.10000,0.01200),V(20.84700,-19.10000,0.01200),V(20.84700,-15.40000,0.01200),V(18.82000,-15.40000,0.01200),V(16.79300,-15.40000,0.01200),V(16.79300,-19.10000,0.01200),V(18.82000,-19.10000,0.01200)]), _poly([V(15.65000,-4.87500,0.01200),V(15.65000,-5.00000,0.01200),V(15.90000,-5.00000,0.01200),V(15.90000,-4.87500,0.01200),V(15.90000,-4.75000,0.01200),V(15.65000,-4.75000,0.01200),V(15.65000,-4.87500,0.01200)]), _poly([V(13.22500,-8.90000,0.01200),V(13.35000,-8.90000,0.01200),V(13.35000,-8.65000,0.01200),V(13.22500,-8.65000,0.01200),V(13.10000,-8.65000,0.01200),V(13.10000,-8.90000,0.01200),V(13.22500,-8.90000,0.01200)]), _poly([V(17.79000,-12.60000,0.01200),V(17.79000,-10.75000,0.01200),V(13.25000,-10.75000,0.01200),V(13.25000,-12.60000,0.01200),V(13.25000,-14.45000,0.01200),V(17.79000,-14.45000,0.01200),V(17.79000,-12.60000,0.01200)]), _poly([V(22.44000,-14.45000,0.01200),V(22.44000,-10.75000,0.01200),V(17.90000,-10.75000,0.01200),V(17.90000,-12.60000,0.01200),V(17.90000,-14.45000,0.01200),V(18.82000,-14.45000,0.01200),V(22.44000,-14.45000,0.01200)]), _poly([V(36.82000,-6.25000,0.01200),V(36.82000,-4.68900,0.01200),V(33.12000,-4.68900,0.01200),V(33.12000,-7.81100,0.01200),V(34.22500,-7.81100,0.01200),V(36.82000,-7.81100,0.01200),V(36.82000,-6.25000,0.01200)]), _poly([V(37.20000,-4.30000,0.01200),V(37.07500,-4.30000,0.01200),V(36.95000,-4.30000,0.01200),V(36.95000,-4.55000,0.01200),V(37.07500,-4.55000,0.01200),V(37.20000,-4.55000,0.01200),V(37.20000,-4.30000,0.01200)]), _poly([V(43.25000,-8.02500,0.01200),V(43.25000,-8.15000,0.01200),V(43.50000,-8.15000,0.01200),V(43.50000,-8.02500,0.01200),V(43.50000,-7.90000,0.01200),V(43.25000,-7.90000,0.01200),V(43.25000,-8.02500,0.01200)]), _poly([V(39.12000,-8.31000,0.01200),V(40.97000,-8.31000,0.01200),V(42.82000,-8.31000,0.01200),V(42.82000,-8.02500,0.01200),V(42.82000,-4.89000,0.01200),V(39.12000,-4.89000,0.01200),V(39.12000,-8.31000,0.01200)]), _poly([V(40.67500,-12.60000,0.01200),V(41.84700,-12.60000,0.01200),V(41.84700,-8.90000,0.01200),V(40.97000,-8.90000,0.01200),V(37.79300,-8.90000,0.01200),V(37.79300,-12.60000,0.01200),V(40.67500,-12.60000,0.01200)]), _poly([V(40.67500,-13.25000,0.01200),V(40.80000,-13.25000,0.01200),V(40.80000,-13.00000,0.01200),V(40.67500,-13.00000,0.01200),V(40.55000,-13.00000,0.01200),V(40.55000,-13.25000,0.01200),V(40.67500,-13.25000,0.01200)]), _poly([V(42.15000,-14.02500,0.01200),V(42.15000,-13.90000,0.01200),V(41.90000,-13.90000,0.01200),V(41.90000,-14.02500,0.01200),V(41.90000,-14.15000,0.01200),V(42.15000,-14.15000,0.01200),V(42.15000,-14.02500,0.01200)])]).extrude(V(0,0,0.03000)))
_add('Routing Dielectric' + '_L4', _fuse(_s), (0.9608,0.5098,0.1922), surface=True)
# --- layer 11 (300 Ohms RES) : z 0.0420..0.0570 mm ---
_s = []
_s.append(Part.Face([_poly([V(19.52000,-18.42700,0.04200),V(19.52000,-16.07300,0.04200),V(18.12000,-16.07300,0.04200),V(18.12000,-18.42700,0.04200),V(19.52000,-18.42700,0.04200)])]).extrude(V(0,0,0.01500)))
_add('300 Ohms RES' + '_L11', _fuse(_s), (0.9020,0.7451,1.0000), surface=True)
# --- layer 13 (3K Ohms RES) : z 0.0570..0.0720 mm ---
_s = []
_s.append(Part.Face([_poly([V(44.92000,-17.88300,0.05700),V(43.52000,-17.88300,0.05700),V(43.52000,-15.41700,0.05700),V(44.92000,-15.41700,0.05700),V(44.92000,-17.88300,0.05700)])]).extrude(V(0,0,0.01500)))
_s.append(Part.Face([_poly([V(33.43700,-13.15000,0.05700),V(35.90300,-13.15000,0.05700),V(35.90300,-14.55000,0.05700),V(33.43700,-14.55000,0.05700),V(33.43700,-13.15000,0.05700)])]).extrude(V(0,0,0.01500)))
_s.append(Part.Face([_poly([V(44.77000,-11.11700,0.05700),V(44.77000,-13.58300,0.05700),V(43.37000,-13.58300,0.05700),V(43.37000,-11.11700,0.05700),V(44.77000,-11.11700,0.05700)])]).extrude(V(0,0,0.01500)))
_s.append(Part.Face([_poly([V(40.99700,-10.05000,0.05700),V(40.99700,-11.45000,0.05700),V(38.64300,-11.45000,0.05700),V(38.64300,-10.05000,0.05700),V(40.99700,-10.05000,0.05700)])]).extrude(V(0,0,0.01500)))
_s.append(Part.Face([_poly([V(26.67000,-6.21700,0.05700),V(26.67000,-8.68300,0.05700),V(25.27000,-8.68300,0.05700),V(25.27000,-6.21700,0.05700),V(26.67000,-6.21700,0.05700)])]).extrude(V(0,0,0.01500)))
_s.append(Part.Face([_poly([V(34.27000,-6.96100,0.05700),V(34.27000,-5.53900,0.05700),V(35.67000,-5.53900,0.05700),V(35.67000,-6.96100,0.05700),V(34.27000,-6.96100,0.05700)])]).extrude(V(0,0,0.01500)))
_add('3K Ohms RES' + '_L13', _fuse(_s), (1.0000,0.9804,0.7843), surface=True)
# --- layer 14 (10K Ohms RES) : z 0.0720..0.0870 mm ---
_s = []
_s.append(Part.Face([_poly([V(41.17000,-17.91000,0.07200),V(41.17000,-16.19000,0.07200),V(42.57000,-16.19000,0.07200),V(42.57000,-17.91000,0.07200),V(41.17000,-17.91000,0.07200)])]).extrude(V(0,0,0.01500)))
_s.append(Part.Face([_poly([V(30.33000,-6.00000,0.07200),V(30.33000,-7.40000,0.07200),V(28.61000,-7.40000,0.07200),V(28.61000,-6.00000,0.07200),V(30.33000,-6.00000,0.07200)])]).extrude(V(0,0,0.01500)))
_s.append(Part.Face([_poly([V(40.27000,-5.74000,0.07200),V(41.67000,-5.74000,0.07200),V(41.67000,-7.46000,0.07200),V(40.27000,-7.46000,0.07200),V(40.27000,-5.74000,0.07200)])]).extrude(V(0,0,0.01500)))
_add('10K Ohms RES' + '_L14', _fuse(_s), (0.5020,0.0000,0.0000), surface=True)
# --- layer 15 (30K Ohms RES) : z 0.0870..0.1020 mm ---
_s = []
_s.append(Part.Face([_poly([V(32.72000,-15.87300,0.08700),V(32.72000,-18.22700,0.08700),V(31.32000,-18.22700,0.08700),V(31.32000,-15.87300,0.08700),V(32.72000,-15.87300,0.08700)])]).extrude(V(0,0,0.01500)))
_s.append(Part.Face([_poly([V(11.52000,-10.77300,0.08700),V(11.52000,-13.12700,0.08700),V(10.12000,-13.12700,0.08700),V(10.12000,-10.77300,0.08700),V(11.52000,-10.77300,0.08700)])]).extrude(V(0,0,0.01500)))
_add('30K Ohms RES' + '_L15', _fuse(_s), (0.6667,1.0000,0.7647), surface=True)
# --- layer 16 (100K Ohms RES) : z 0.1020..0.1170 mm ---
_s = []
_s.append(Part.Face([_poly([V(16.94000,-13.30000,0.10200),V(14.10000,-13.30000,0.10200),V(14.10000,-11.90000,0.10200),V(16.94000,-11.90000,0.10200),V(16.94000,-13.30000,0.10200)])]).extrude(V(0,0,0.01500)))
_s.append(Part.Face([_poly([V(21.59000,-13.30000,0.10200),V(18.75000,-13.30000,0.10200),V(18.75000,-11.90000,0.10200),V(21.59000,-11.90000,0.10200),V(21.59000,-13.30000,0.10200)])]).extrude(V(0,0,0.01500)))
_add('100K Ohms RES' + '_L16', _fuse(_s), (0.9020,0.0980,0.2941), surface=True)
# --- layer 17 (300K Ohms RES) : z 0.1170..0.1320 mm ---
_s = []
_s.append(Part.Face([_poly([V(34.49300,-17.30000,0.11700),V(36.84700,-17.30000,0.11700),V(36.84700,-15.90000,0.11700),V(34.49300,-15.90000,0.11700),V(34.49300,-17.30000,0.11700)])]).extrude(V(0,0,0.01500)))
_add('300K Ohms RES' + '_L17', _fuse(_s), (0.2353,0.7059,0.2941), surface=True)
# --- layer 19 (Resister Glaze) : z 0.1320..0.1520 mm ---
_s = []
_s.append(Part.Face([_poly([V(19.82000,-15.77300,0.13200),V(19.82000,-18.72700,0.13200),V(17.82000,-18.72700,0.13200),V(17.82000,-15.77300,0.13200),V(19.82000,-15.77300,0.13200)])]).extrude(V(0,0,0.02000)))
_s.append(Part.Face([_poly([V(31.02000,-15.57300,0.13200),V(33.02000,-15.57300,0.13200),V(33.02000,-18.52700,0.13200),V(31.02000,-18.52700,0.13200),V(31.02000,-15.57300,0.13200)])]).extrude(V(0,0,0.02000)))
_s.append(Part.Face([_poly([V(36.20300,-12.85000,0.13200),V(36.20300,-14.85000,0.13200),V(33.13700,-14.85000,0.13200),V(33.13700,-12.85000,0.13200),V(36.20300,-12.85000,0.13200)])]).extrude(V(0,0,0.02000)))
_s.append(Part.Face([_poly([V(17.24000,-11.60000,0.13200),V(17.24000,-13.60000,0.13200),V(13.80000,-13.60000,0.13200),V(13.80000,-11.60000,0.13200),V(17.24000,-11.60000,0.13200)])]).extrude(V(0,0,0.02000)))
_s.append(Part.Face([_poly([V(21.89000,-11.60000,0.13200),V(21.89000,-13.60000,0.13200),V(18.45000,-13.60000,0.13200),V(18.45000,-11.60000,0.13200),V(21.89000,-11.60000,0.13200)])]).extrude(V(0,0,0.02000)))
_s.append(Part.Face([_poly([V(9.82000,-10.47300,0.13200),V(11.82000,-10.47300,0.13200),V(11.82000,-13.42700,0.13200),V(9.82000,-13.42700,0.13200),V(9.82000,-10.47300,0.13200)])]).extrude(V(0,0,0.02000)))
_s.append(Part.Face([_poly([V(26.97000,-8.98300,0.13200),V(24.97000,-8.98300,0.13200),V(24.97000,-5.91700,0.13200),V(26.97000,-5.91700,0.13200),V(26.97000,-8.98300,0.13200)])]).extrude(V(0,0,0.02000)))
_s.append(Part.Face([_poly([V(28.31000,-7.70000,0.13200),V(28.31000,-5.70000,0.13200),V(30.63000,-5.70000,0.13200),V(30.63000,-7.70000,0.13200),V(28.31000,-7.70000,0.13200)])]).extrude(V(0,0,0.02000)))
_s.append(Part.Face([_poly([V(42.87000,-18.21000,0.13200),V(40.87000,-18.21000,0.13200),V(40.87000,-15.89000,0.13200),V(42.87000,-15.89000,0.13200),V(42.87000,-18.21000,0.13200)])]).extrude(V(0,0,0.02000)))
_s.append(Part.Face([_poly([V(43.22000,-15.11700,0.13200),V(45.22000,-15.11700,0.13200),V(45.22000,-18.18300,0.13200),V(43.22000,-18.18300,0.13200),V(43.22000,-15.11700,0.13200)])]).extrude(V(0,0,0.02000)))
_s.append(Part.Face([_poly([V(34.19300,-17.60000,0.13200),V(34.19300,-15.60000,0.13200),V(37.14700,-15.60000,0.13200),V(37.14700,-17.60000,0.13200),V(34.19300,-17.60000,0.13200)])]).extrude(V(0,0,0.02000)))
_s.append(Part.Face([_poly([V(45.07000,-13.88300,0.13200),V(43.07000,-13.88300,0.13200),V(43.07000,-10.81700,0.13200),V(45.07000,-10.81700,0.13200),V(45.07000,-13.88300,0.13200)])]).extrude(V(0,0,0.02000)))
_s.append(Part.Face([_poly([V(38.34300,-11.75000,0.13200),V(38.34300,-9.75000,0.13200),V(41.29700,-9.75000,0.13200),V(41.29700,-11.75000,0.13200),V(38.34300,-11.75000,0.13200)])]).extrude(V(0,0,0.02000)))
_s.append(Part.Face([_poly([V(41.97000,-7.76000,0.13200),V(39.97000,-7.76000,0.13200),V(39.97000,-5.44000,0.13200),V(41.97000,-5.44000,0.13200),V(41.97000,-7.76000,0.13200)])]).extrude(V(0,0,0.02000)))
_s.append(Part.Face([_poly([V(33.97000,-5.23900,0.13200),V(35.97000,-5.23900,0.13200),V(35.97000,-7.26100,0.13200),V(33.97000,-7.26100,0.13200),V(33.97000,-5.23900,0.13200)])]).extrude(V(0,0,0.02000)))
_add('Resister Glaze' + '_L19', _fuse(_s), (0.2000,0.7200,0.3500), surface=True, transparency=55)
# --- layer 49 (L49) : z 0.1520..0.1620 mm ---
_s = []
_s.append(Part.Face([_poly([V(10.07000,-22.57000,-0.63500),V(9.94800,-22.67000,-0.63500),V(9.80800,-22.74500,-0.63500),V(9.65700,-22.79100,-0.63500),V(9.50000,-22.80600,-0.63500),V(9.34300,-22.79100,-0.63500),V(9.19200,-22.74500,-0.63500),V(9.05200,-22.67000,-0.63500),V(8.93000,-22.57000,-0.63500),V(8.83000,-22.44800,-0.63500),V(8.75500,-22.30800,-0.63500),V(8.70900,-22.15700,-0.63500),V(8.69400,-22.00000,-0.63500),V(8.70900,-21.84300,-0.63500),V(8.75500,-21.69200,-0.63500),V(8.83000,-21.55200,-0.63500),V(8.93000,-21.43000,-0.63500),V(9.05200,-21.33000,-0.63500),V(9.19200,-21.25500,-0.63500),V(9.34300,-21.20900,-0.63500),V(9.50000,-21.19400,-0.63500),V(9.65700,-21.20900,-0.63500),V(9.80800,-21.25500,-0.63500),V(9.94800,-21.33000,-0.63500),V(10.07000,-21.43000,-0.63500),V(10.17000,-21.55200,-0.63500),V(10.24500,-21.69200,-0.63500),V(10.29100,-21.84300,-0.63500),V(10.30600,-22.00000,-0.63500),V(10.29100,-22.15700,-0.63500),V(10.24500,-22.30800,-0.63500),V(10.17000,-22.44800,-0.63500),V(10.07000,-22.57000,-0.63500)])]).extrude(V(0,0,0.79700)))
_s.append(Part.Face([_poly([V(12.48800,-22.67000,-0.63500),V(12.34800,-22.74500,-0.63500),V(12.19700,-22.79100,-0.63500),V(12.04000,-22.80600,-0.63500),V(11.88300,-22.79100,-0.63500),V(11.73200,-22.74500,-0.63500),V(11.59200,-22.67000,-0.63500),V(11.47000,-22.57000,-0.63500),V(11.37000,-22.44800,-0.63500),V(11.29500,-22.30800,-0.63500),V(11.24900,-22.15700,-0.63500),V(11.23400,-22.00000,-0.63500),V(11.24900,-21.84300,-0.63500),V(11.29500,-21.69200,-0.63500),V(11.37000,-21.55200,-0.63500),V(11.47000,-21.43000,-0.63500),V(11.59200,-21.33000,-0.63500),V(11.73200,-21.25500,-0.63500),V(11.88300,-21.20900,-0.63500),V(12.04000,-21.19400,-0.63500),V(12.19700,-21.20900,-0.63500),V(12.34800,-21.25500,-0.63500),V(12.48800,-21.33000,-0.63500),V(12.61000,-21.43000,-0.63500),V(12.71000,-21.55200,-0.63500),V(12.78500,-21.69200,-0.63500),V(12.83100,-21.84300,-0.63500),V(12.84600,-22.00000,-0.63500),V(12.83100,-22.15700,-0.63500),V(12.78500,-22.30800,-0.63500),V(12.71000,-22.44800,-0.63500),V(12.61000,-22.57000,-0.63500),V(12.48800,-22.67000,-0.63500)])]).extrude(V(0,0,0.79700)))
_s.append(Part.Face([_poly([V(15.02800,-22.67000,-0.63500),V(14.88800,-22.74500,-0.63500),V(14.73700,-22.79100,-0.63500),V(14.58000,-22.80600,-0.63500),V(14.42300,-22.79100,-0.63500),V(14.27200,-22.74500,-0.63500),V(14.13200,-22.67000,-0.63500),V(14.01000,-22.57000,-0.63500),V(13.91000,-22.44800,-0.63500),V(13.83500,-22.30800,-0.63500),V(13.78900,-22.15700,-0.63500),V(13.77400,-22.00000,-0.63500),V(13.78900,-21.84300,-0.63500),V(13.83500,-21.69200,-0.63500),V(13.91000,-21.55200,-0.63500),V(14.01000,-21.43000,-0.63500),V(14.13200,-21.33000,-0.63500),V(14.27200,-21.25500,-0.63500),V(14.42300,-21.20900,-0.63500),V(14.58000,-21.19400,-0.63500),V(14.73700,-21.20900,-0.63500),V(14.88800,-21.25500,-0.63500),V(15.02800,-21.33000,-0.63500),V(15.15000,-21.43000,-0.63500),V(15.25000,-21.55200,-0.63500),V(15.32500,-21.69200,-0.63500),V(15.37100,-21.84300,-0.63500),V(15.38600,-22.00000,-0.63500),V(15.37100,-22.15700,-0.63500),V(15.32500,-22.30800,-0.63500),V(15.25000,-22.44800,-0.63500),V(15.15000,-22.57000,-0.63500),V(15.02800,-22.67000,-0.63500)])]).extrude(V(0,0,0.79700)))
_s.append(Part.Face([_poly([V(17.56800,-22.67000,-0.63500),V(17.42800,-22.74500,-0.63500),V(17.27700,-22.79100,-0.63500),V(17.12000,-22.80600,-0.63500),V(16.96300,-22.79100,-0.63500),V(16.81200,-22.74500,-0.63500),V(16.67200,-22.67000,-0.63500),V(16.55000,-22.57000,-0.63500),V(16.45000,-22.44800,-0.63500),V(16.37500,-22.30800,-0.63500),V(16.32900,-22.15700,-0.63500),V(16.31400,-22.00000,-0.63500),V(16.32900,-21.84300,-0.63500),V(16.37500,-21.69200,-0.63500),V(16.45000,-21.55200,-0.63500),V(16.55000,-21.43000,-0.63500),V(16.67200,-21.33000,-0.63500),V(16.81200,-21.25500,-0.63500),V(16.96300,-21.20900,-0.63500),V(17.12000,-21.19400,-0.63500),V(17.27700,-21.20900,-0.63500),V(17.42800,-21.25500,-0.63500),V(17.56800,-21.33000,-0.63500),V(17.69000,-21.43000,-0.63500),V(17.79000,-21.55200,-0.63500),V(17.86500,-21.69200,-0.63500),V(17.91100,-21.84300,-0.63500),V(17.92600,-22.00000,-0.63500),V(17.91100,-22.15700,-0.63500),V(17.86500,-22.30800,-0.63500),V(17.79000,-22.44800,-0.63500),V(17.69000,-22.57000,-0.63500),V(17.56800,-22.67000,-0.63500)])]).extrude(V(0,0,0.79700)))
_s.append(Part.Face([_poly([V(20.10800,-22.67000,-0.63500),V(19.96800,-22.74500,-0.63500),V(19.81700,-22.79100,-0.63500),V(19.66000,-22.80600,-0.63500),V(19.50300,-22.79100,-0.63500),V(19.35200,-22.74500,-0.63500),V(19.21200,-22.67000,-0.63500),V(19.09000,-22.57000,-0.63500),V(18.99000,-22.44800,-0.63500),V(18.91500,-22.30800,-0.63500),V(18.86900,-22.15700,-0.63500),V(18.85400,-22.00000,-0.63500),V(18.86900,-21.84300,-0.63500),V(18.91500,-21.69200,-0.63500),V(18.99000,-21.55200,-0.63500),V(19.09000,-21.43000,-0.63500),V(19.21200,-21.33000,-0.63500),V(19.35200,-21.25500,-0.63500),V(19.50300,-21.20900,-0.63500),V(19.66000,-21.19400,-0.63500),V(19.81700,-21.20900,-0.63500),V(19.96800,-21.25500,-0.63500),V(20.10800,-21.33000,-0.63500),V(20.23000,-21.43000,-0.63500),V(20.33000,-21.55200,-0.63500),V(20.40500,-21.69200,-0.63500),V(20.45100,-21.84300,-0.63500),V(20.46600,-22.00000,-0.63500),V(20.45100,-22.15700,-0.63500),V(20.40500,-22.30800,-0.63500),V(20.33000,-22.44800,-0.63500),V(20.23000,-22.57000,-0.63500),V(20.10800,-22.67000,-0.63500)])]).extrude(V(0,0,0.79700)))
_s.append(Part.Face([_poly([V(22.64800,-22.67000,-0.63500),V(22.50800,-22.74500,-0.63500),V(22.35700,-22.79100,-0.63500),V(22.20000,-22.80600,-0.63500),V(22.04300,-22.79100,-0.63500),V(21.89200,-22.74500,-0.63500),V(21.75200,-22.67000,-0.63500),V(21.63000,-22.57000,-0.63500),V(21.53000,-22.44800,-0.63500),V(21.45500,-22.30800,-0.63500),V(21.40900,-22.15700,-0.63500),V(21.39400,-22.00000,-0.63500),V(21.40900,-21.84300,-0.63500),V(21.45500,-21.69200,-0.63500),V(21.53000,-21.55200,-0.63500),V(21.63000,-21.43000,-0.63500),V(21.75200,-21.33000,-0.63500),V(21.89200,-21.25500,-0.63500),V(22.04300,-21.20900,-0.63500),V(22.20000,-21.19400,-0.63500),V(22.35700,-21.20900,-0.63500),V(22.50800,-21.25500,-0.63500),V(22.64800,-21.33000,-0.63500),V(22.77000,-21.43000,-0.63500),V(22.87000,-21.55200,-0.63500),V(22.94500,-21.69200,-0.63500),V(22.99100,-21.84300,-0.63500),V(23.00600,-22.00000,-0.63500),V(22.99100,-22.15700,-0.63500),V(22.94500,-22.30800,-0.63500),V(22.87000,-22.44800,-0.63500),V(22.77000,-22.57000,-0.63500),V(22.64800,-22.67000,-0.63500)])]).extrude(V(0,0,0.79700)))
_s.append(Part.Face([_poly([V(25.18800,-22.67000,-0.63500),V(25.04800,-22.74500,-0.63500),V(24.89700,-22.79100,-0.63500),V(24.74000,-22.80600,-0.63500),V(24.58300,-22.79100,-0.63500),V(24.43200,-22.74500,-0.63500),V(24.29200,-22.67000,-0.63500),V(24.17000,-22.57000,-0.63500),V(24.07000,-22.44800,-0.63500),V(23.99500,-22.30800,-0.63500),V(23.94900,-22.15700,-0.63500),V(23.93400,-22.00000,-0.63500),V(23.94900,-21.84300,-0.63500),V(23.99500,-21.69200,-0.63500),V(24.07000,-21.55200,-0.63500),V(24.17000,-21.43000,-0.63500),V(24.29200,-21.33000,-0.63500),V(24.43200,-21.25500,-0.63500),V(24.58300,-21.20900,-0.63500),V(24.74000,-21.19400,-0.63500),V(24.89700,-21.20900,-0.63500),V(25.04800,-21.25500,-0.63500),V(25.18800,-21.33000,-0.63500),V(25.31000,-21.43000,-0.63500),V(25.41000,-21.55200,-0.63500),V(25.48500,-21.69200,-0.63500),V(25.53100,-21.84300,-0.63500),V(25.54600,-22.00000,-0.63500),V(25.53100,-22.15700,-0.63500),V(25.48500,-22.30800,-0.63500),V(25.41000,-22.44800,-0.63500),V(25.31000,-22.57000,-0.63500),V(25.18800,-22.67000,-0.63500)])]).extrude(V(0,0,0.79700)))
_s.append(Part.Face([_poly([V(27.72800,-22.67000,-0.63500),V(27.58800,-22.74500,-0.63500),V(27.43700,-22.79100,-0.63500),V(27.28000,-22.80600,-0.63500),V(27.12300,-22.79100,-0.63500),V(26.97200,-22.74500,-0.63500),V(26.83200,-22.67000,-0.63500),V(26.71000,-22.57000,-0.63500),V(26.61000,-22.44800,-0.63500),V(26.53500,-22.30800,-0.63500),V(26.48900,-22.15700,-0.63500),V(26.47400,-22.00000,-0.63500),V(26.48900,-21.84300,-0.63500),V(26.53500,-21.69200,-0.63500),V(26.61000,-21.55200,-0.63500),V(26.71000,-21.43000,-0.63500),V(26.83200,-21.33000,-0.63500),V(26.97200,-21.25500,-0.63500),V(27.12300,-21.20900,-0.63500),V(27.28000,-21.19400,-0.63500),V(27.43700,-21.20900,-0.63500),V(27.58800,-21.25500,-0.63500),V(27.72800,-21.33000,-0.63500),V(27.85000,-21.43000,-0.63500),V(27.95000,-21.55200,-0.63500),V(28.02500,-21.69200,-0.63500),V(28.07100,-21.84300,-0.63500),V(28.08600,-22.00000,-0.63500),V(28.07100,-22.15700,-0.63500),V(28.02500,-22.30800,-0.63500),V(27.95000,-22.44800,-0.63500),V(27.85000,-22.57000,-0.63500),V(27.72800,-22.67000,-0.63500)])]).extrude(V(0,0,0.79700)))
_s.append(Part.Face([_poly([V(9.94800,-1.81000,-0.63500),V(9.80800,-1.88500,-0.63500),V(9.65700,-1.93100,-0.63500),V(9.50000,-1.94600,-0.63500),V(9.34300,-1.93100,-0.63500),V(9.19200,-1.88500,-0.63500),V(9.05200,-1.81000,-0.63500),V(8.93000,-1.71000,-0.63500),V(8.83000,-1.58800,-0.63500),V(8.75500,-1.44800,-0.63500),V(8.70900,-1.29700,-0.63500),V(8.69400,-1.14000,-0.63500),V(8.70900,-0.98300,-0.63500),V(8.75500,-0.83200,-0.63500),V(8.83000,-0.69200,-0.63500),V(8.93000,-0.57000,-0.63500),V(9.05200,-0.47000,-0.63500),V(9.19200,-0.39500,-0.63500),V(9.34300,-0.34900,-0.63500),V(9.50000,-0.33400,-0.63500),V(9.65700,-0.34900,-0.63500),V(9.80800,-0.39500,-0.63500),V(9.94800,-0.47000,-0.63500),V(10.07000,-0.57000,-0.63500),V(10.17000,-0.69200,-0.63500),V(10.24500,-0.83200,-0.63500),V(10.29100,-0.98300,-0.63500),V(10.30600,-1.14000,-0.63500),V(10.29100,-1.29700,-0.63500),V(10.24500,-1.44800,-0.63500),V(10.17000,-1.58800,-0.63500),V(10.07000,-1.71000,-0.63500),V(9.94800,-1.81000,-0.63500)])]).extrude(V(0,0,0.79700)))
_s.append(Part.Face([_poly([V(12.48800,-1.81000,-0.63500),V(12.34800,-1.88500,-0.63500),V(12.19700,-1.93100,-0.63500),V(12.04000,-1.94600,-0.63500),V(11.88300,-1.93100,-0.63500),V(11.73200,-1.88500,-0.63500),V(11.59200,-1.81000,-0.63500),V(11.47000,-1.71000,-0.63500),V(11.37000,-1.58800,-0.63500),V(11.29500,-1.44800,-0.63500),V(11.24900,-1.29700,-0.63500),V(11.23400,-1.14000,-0.63500),V(11.24900,-0.98300,-0.63500),V(11.29500,-0.83200,-0.63500),V(11.37000,-0.69200,-0.63500),V(11.47000,-0.57000,-0.63500),V(11.59200,-0.47000,-0.63500),V(11.73200,-0.39500,-0.63500),V(11.88300,-0.34900,-0.63500),V(12.04000,-0.33400,-0.63500),V(12.19700,-0.34900,-0.63500),V(12.34800,-0.39500,-0.63500),V(12.48800,-0.47000,-0.63500),V(12.61000,-0.57000,-0.63500),V(12.71000,-0.69200,-0.63500),V(12.78500,-0.83200,-0.63500),V(12.83100,-0.98300,-0.63500),V(12.84600,-1.14000,-0.63500),V(12.83100,-1.29700,-0.63500),V(12.78500,-1.44800,-0.63500),V(12.71000,-1.58800,-0.63500),V(12.61000,-1.71000,-0.63500),V(12.48800,-1.81000,-0.63500)])]).extrude(V(0,0,0.79700)))
_s.append(Part.Face([_poly([V(15.02800,-1.81000,-0.63500),V(14.88800,-1.88500,-0.63500),V(14.73700,-1.93100,-0.63500),V(14.58000,-1.94600,-0.63500),V(14.42300,-1.93100,-0.63500),V(14.27200,-1.88500,-0.63500),V(14.13200,-1.81000,-0.63500),V(14.01000,-1.71000,-0.63500),V(13.91000,-1.58800,-0.63500),V(13.83500,-1.44800,-0.63500),V(13.78900,-1.29700,-0.63500),V(13.77400,-1.14000,-0.63500),V(13.78900,-0.98300,-0.63500),V(13.83500,-0.83200,-0.63500),V(13.91000,-0.69200,-0.63500),V(14.01000,-0.57000,-0.63500),V(14.13200,-0.47000,-0.63500),V(14.27200,-0.39500,-0.63500),V(14.42300,-0.34900,-0.63500),V(14.58000,-0.33400,-0.63500),V(14.73700,-0.34900,-0.63500),V(14.88800,-0.39500,-0.63500),V(15.02800,-0.47000,-0.63500),V(15.15000,-0.57000,-0.63500),V(15.25000,-0.69200,-0.63500),V(15.32500,-0.83200,-0.63500),V(15.37100,-0.98300,-0.63500),V(15.38600,-1.14000,-0.63500),V(15.37100,-1.29700,-0.63500),V(15.32500,-1.44800,-0.63500),V(15.25000,-1.58800,-0.63500),V(15.15000,-1.71000,-0.63500),V(15.02800,-1.81000,-0.63500)])]).extrude(V(0,0,0.79700)))
_s.append(Part.Face([_poly([V(17.56800,-1.81000,-0.63500),V(17.42800,-1.88500,-0.63500),V(17.27700,-1.93100,-0.63500),V(17.12000,-1.94600,-0.63500),V(16.96300,-1.93100,-0.63500),V(16.81200,-1.88500,-0.63500),V(16.67200,-1.81000,-0.63500),V(16.55000,-1.71000,-0.63500),V(16.45000,-1.58800,-0.63500),V(16.37500,-1.44800,-0.63500),V(16.32900,-1.29700,-0.63500),V(16.31400,-1.14000,-0.63500),V(16.32900,-0.98300,-0.63500),V(16.37500,-0.83200,-0.63500),V(16.45000,-0.69200,-0.63500),V(16.55000,-0.57000,-0.63500),V(16.67200,-0.47000,-0.63500),V(16.81200,-0.39500,-0.63500),V(16.96300,-0.34900,-0.63500),V(17.12000,-0.33400,-0.63500),V(17.27700,-0.34900,-0.63500),V(17.42800,-0.39500,-0.63500),V(17.56800,-0.47000,-0.63500),V(17.69000,-0.57000,-0.63500),V(17.79000,-0.69200,-0.63500),V(17.86500,-0.83200,-0.63500),V(17.91100,-0.98300,-0.63500),V(17.92600,-1.14000,-0.63500),V(17.91100,-1.29700,-0.63500),V(17.86500,-1.44800,-0.63500),V(17.79000,-1.58800,-0.63500),V(17.69000,-1.71000,-0.63500),V(17.56800,-1.81000,-0.63500)])]).extrude(V(0,0,0.79700)))
_s.append(Part.Face([_poly([V(20.10800,-1.81000,-0.63500),V(19.96800,-1.88500,-0.63500),V(19.81700,-1.93100,-0.63500),V(19.66000,-1.94600,-0.63500),V(19.50300,-1.93100,-0.63500),V(19.35200,-1.88500,-0.63500),V(19.21200,-1.81000,-0.63500),V(19.09000,-1.71000,-0.63500),V(18.99000,-1.58800,-0.63500),V(18.91500,-1.44800,-0.63500),V(18.86900,-1.29700,-0.63500),V(18.85400,-1.14000,-0.63500),V(18.86900,-0.98300,-0.63500),V(18.91500,-0.83200,-0.63500),V(18.99000,-0.69200,-0.63500),V(19.09000,-0.57000,-0.63500),V(19.21200,-0.47000,-0.63500),V(19.35200,-0.39500,-0.63500),V(19.50300,-0.34900,-0.63500),V(19.66000,-0.33400,-0.63500),V(19.81700,-0.34900,-0.63500),V(19.96800,-0.39500,-0.63500),V(20.10800,-0.47000,-0.63500),V(20.23000,-0.57000,-0.63500),V(20.33000,-0.69200,-0.63500),V(20.40500,-0.83200,-0.63500),V(20.45100,-0.98300,-0.63500),V(20.46600,-1.14000,-0.63500),V(20.45100,-1.29700,-0.63500),V(20.40500,-1.44800,-0.63500),V(20.33000,-1.58800,-0.63500),V(20.23000,-1.71000,-0.63500),V(20.10800,-1.81000,-0.63500)])]).extrude(V(0,0,0.79700)))
_s.append(Part.Face([_poly([V(22.64800,-1.81000,-0.63500),V(22.50800,-1.88500,-0.63500),V(22.35700,-1.93100,-0.63500),V(22.20000,-1.94600,-0.63500),V(22.04300,-1.93100,-0.63500),V(21.89200,-1.88500,-0.63500),V(21.75200,-1.81000,-0.63500),V(21.63000,-1.71000,-0.63500),V(21.53000,-1.58800,-0.63500),V(21.45500,-1.44800,-0.63500),V(21.40900,-1.29700,-0.63500),V(21.39400,-1.14000,-0.63500),V(21.40900,-0.98300,-0.63500),V(21.45500,-0.83200,-0.63500),V(21.53000,-0.69200,-0.63500),V(21.63000,-0.57000,-0.63500),V(21.75200,-0.47000,-0.63500),V(21.89200,-0.39500,-0.63500),V(22.04300,-0.34900,-0.63500),V(22.20000,-0.33400,-0.63500),V(22.35700,-0.34900,-0.63500),V(22.50800,-0.39500,-0.63500),V(22.64800,-0.47000,-0.63500),V(22.77000,-0.57000,-0.63500),V(22.87000,-0.69200,-0.63500),V(22.94500,-0.83200,-0.63500),V(22.99100,-0.98300,-0.63500),V(23.00600,-1.14000,-0.63500),V(22.99100,-1.29700,-0.63500),V(22.94500,-1.44800,-0.63500),V(22.87000,-1.58800,-0.63500),V(22.77000,-1.71000,-0.63500),V(22.64800,-1.81000,-0.63500)])]).extrude(V(0,0,0.79700)))
_s.append(Part.Face([_poly([V(25.18800,-1.81000,-0.63500),V(25.04800,-1.88500,-0.63500),V(24.89700,-1.93100,-0.63500),V(24.74000,-1.94600,-0.63500),V(24.58300,-1.93100,-0.63500),V(24.43200,-1.88500,-0.63500),V(24.29200,-1.81000,-0.63500),V(24.17000,-1.71000,-0.63500),V(24.07000,-1.58800,-0.63500),V(23.99500,-1.44800,-0.63500),V(23.94900,-1.29700,-0.63500),V(23.93400,-1.14000,-0.63500),V(23.94900,-0.98300,-0.63500),V(23.99500,-0.83200,-0.63500),V(24.07000,-0.69200,-0.63500),V(24.17000,-0.57000,-0.63500),V(24.29200,-0.47000,-0.63500),V(24.43200,-0.39500,-0.63500),V(24.58300,-0.34900,-0.63500),V(24.74000,-0.33400,-0.63500),V(24.89700,-0.34900,-0.63500),V(25.04800,-0.39500,-0.63500),V(25.18800,-0.47000,-0.63500),V(25.31000,-0.57000,-0.63500),V(25.41000,-0.69200,-0.63500),V(25.48500,-0.83200,-0.63500),V(25.53100,-0.98300,-0.63500),V(25.54600,-1.14000,-0.63500),V(25.53100,-1.29700,-0.63500),V(25.48500,-1.44800,-0.63500),V(25.41000,-1.58800,-0.63500),V(25.31000,-1.71000,-0.63500),V(25.18800,-1.81000,-0.63500)])]).extrude(V(0,0,0.79700)))
_s.append(Part.Face([_poly([V(30.39000,-22.57000,-0.63500),V(30.26800,-22.67000,-0.63500),V(30.12800,-22.74500,-0.63500),V(29.97700,-22.79100,-0.63500),V(29.82000,-22.80600,-0.63500),V(29.66300,-22.79100,-0.63500),V(29.51200,-22.74500,-0.63500),V(29.37200,-22.67000,-0.63500),V(29.25000,-22.57000,-0.63500),V(29.15000,-22.44800,-0.63500),V(29.07500,-22.30800,-0.63500),V(29.02900,-22.15700,-0.63500),V(29.01400,-22.00000,-0.63500),V(29.02900,-21.84300,-0.63500),V(29.07500,-21.69200,-0.63500),V(29.15000,-21.55200,-0.63500),V(29.25000,-21.43000,-0.63500),V(29.37200,-21.33000,-0.63500),V(29.51200,-21.25500,-0.63500),V(29.66300,-21.20900,-0.63500),V(29.82000,-21.19400,-0.63500),V(29.97700,-21.20900,-0.63500),V(30.12800,-21.25500,-0.63500),V(30.26800,-21.33000,-0.63500),V(30.39000,-21.43000,-0.63500),V(30.49000,-21.55200,-0.63500),V(30.56500,-21.69200,-0.63500),V(30.61100,-21.84300,-0.63500),V(30.62600,-22.00000,-0.63500),V(30.61100,-22.15700,-0.63500),V(30.56500,-22.30800,-0.63500),V(30.49000,-22.44800,-0.63500),V(30.39000,-22.57000,-0.63500)])]).extrude(V(0,0,0.79700)))
_s.append(Part.Face([_poly([V(32.80800,-22.67000,-0.63500),V(32.66800,-22.74500,-0.63500),V(32.51700,-22.79100,-0.63500),V(32.36000,-22.80600,-0.63500),V(32.20300,-22.79100,-0.63500),V(32.05200,-22.74500,-0.63500),V(31.91200,-22.67000,-0.63500),V(31.79000,-22.57000,-0.63500),V(31.69000,-22.44800,-0.63500),V(31.61500,-22.30800,-0.63500),V(31.56900,-22.15700,-0.63500),V(31.55400,-22.00000,-0.63500),V(31.56900,-21.84300,-0.63500),V(31.61500,-21.69200,-0.63500),V(31.69000,-21.55200,-0.63500),V(31.79000,-21.43000,-0.63500),V(31.91200,-21.33000,-0.63500),V(32.05200,-21.25500,-0.63500),V(32.20300,-21.20900,-0.63500),V(32.36000,-21.19400,-0.63500),V(32.51700,-21.20900,-0.63500),V(32.66800,-21.25500,-0.63500),V(32.80800,-21.33000,-0.63500),V(32.93000,-21.43000,-0.63500),V(33.03000,-21.55200,-0.63500),V(33.10500,-21.69200,-0.63500),V(33.15100,-21.84300,-0.63500),V(33.16600,-22.00000,-0.63500),V(33.15100,-22.15700,-0.63500),V(33.10500,-22.30800,-0.63500),V(33.03000,-22.44800,-0.63500),V(32.93000,-22.57000,-0.63500),V(32.80800,-22.67000,-0.63500)])]).extrude(V(0,0,0.79700)))
_s.append(Part.Face([_poly([V(35.34800,-22.67000,-0.63500),V(35.20800,-22.74500,-0.63500),V(35.05700,-22.79100,-0.63500),V(34.90000,-22.80600,-0.63500),V(34.74300,-22.79100,-0.63500),V(34.59200,-22.74500,-0.63500),V(34.45200,-22.67000,-0.63500),V(34.33000,-22.57000,-0.63500),V(34.23000,-22.44800,-0.63500),V(34.15500,-22.30800,-0.63500),V(34.10900,-22.15700,-0.63500),V(34.09400,-22.00000,-0.63500),V(34.10900,-21.84300,-0.63500),V(34.15500,-21.69200,-0.63500),V(34.23000,-21.55200,-0.63500),V(34.33000,-21.43000,-0.63500),V(34.45200,-21.33000,-0.63500),V(34.59200,-21.25500,-0.63500),V(34.74300,-21.20900,-0.63500),V(34.90000,-21.19400,-0.63500),V(35.05700,-21.20900,-0.63500),V(35.20800,-21.25500,-0.63500),V(35.34800,-21.33000,-0.63500),V(35.47000,-21.43000,-0.63500),V(35.57000,-21.55200,-0.63500),V(35.64500,-21.69200,-0.63500),V(35.69100,-21.84300,-0.63500),V(35.70600,-22.00000,-0.63500),V(35.69100,-22.15700,-0.63500),V(35.64500,-22.30800,-0.63500),V(35.57000,-22.44800,-0.63500),V(35.47000,-22.57000,-0.63500),V(35.34800,-22.67000,-0.63500)])]).extrude(V(0,0,0.79700)))
_s.append(Part.Face([_poly([V(37.88800,-22.67000,-0.63500),V(37.74800,-22.74500,-0.63500),V(37.59700,-22.79100,-0.63500),V(37.44000,-22.80600,-0.63500),V(37.28300,-22.79100,-0.63500),V(37.13200,-22.74500,-0.63500),V(36.99200,-22.67000,-0.63500),V(36.87000,-22.57000,-0.63500),V(36.77000,-22.44800,-0.63500),V(36.69500,-22.30800,-0.63500),V(36.64900,-22.15700,-0.63500),V(36.63400,-22.00000,-0.63500),V(36.64900,-21.84300,-0.63500),V(36.69500,-21.69200,-0.63500),V(36.77000,-21.55200,-0.63500),V(36.87000,-21.43000,-0.63500),V(36.99200,-21.33000,-0.63500),V(37.13200,-21.25500,-0.63500),V(37.28300,-21.20900,-0.63500),V(37.44000,-21.19400,-0.63500),V(37.59700,-21.20900,-0.63500),V(37.74800,-21.25500,-0.63500),V(37.88800,-21.33000,-0.63500),V(38.01000,-21.43000,-0.63500),V(38.11000,-21.55200,-0.63500),V(38.18500,-21.69200,-0.63500),V(38.23100,-21.84300,-0.63500),V(38.24600,-22.00000,-0.63500),V(38.23100,-22.15700,-0.63500),V(38.18500,-22.30800,-0.63500),V(38.11000,-22.44800,-0.63500),V(38.01000,-22.57000,-0.63500),V(37.88800,-22.67000,-0.63500)])]).extrude(V(0,0,0.79700)))
_s.append(Part.Face([_poly([V(40.42800,-22.67000,-0.63500),V(40.28800,-22.74500,-0.63500),V(40.13700,-22.79100,-0.63500),V(39.98000,-22.80600,-0.63500),V(39.82300,-22.79100,-0.63500),V(39.67200,-22.74500,-0.63500),V(39.53200,-22.67000,-0.63500),V(39.41000,-22.57000,-0.63500),V(39.31000,-22.44800,-0.63500),V(39.23500,-22.30800,-0.63500),V(39.18900,-22.15700,-0.63500),V(39.17400,-22.00000,-0.63500),V(39.18900,-21.84300,-0.63500),V(39.23500,-21.69200,-0.63500),V(39.31000,-21.55200,-0.63500),V(39.41000,-21.43000,-0.63500),V(39.53200,-21.33000,-0.63500),V(39.67200,-21.25500,-0.63500),V(39.82300,-21.20900,-0.63500),V(39.98000,-21.19400,-0.63500),V(40.13700,-21.20900,-0.63500),V(40.28800,-21.25500,-0.63500),V(40.42800,-21.33000,-0.63500),V(40.55000,-21.43000,-0.63500),V(40.65000,-21.55200,-0.63500),V(40.72500,-21.69200,-0.63500),V(40.77100,-21.84300,-0.63500),V(40.78600,-22.00000,-0.63500),V(40.77100,-22.15700,-0.63500),V(40.72500,-22.30800,-0.63500),V(40.65000,-22.44800,-0.63500),V(40.55000,-22.57000,-0.63500),V(40.42800,-22.67000,-0.63500)])]).extrude(V(0,0,0.79700)))
_s.append(Part.Face([_poly([V(42.96800,-22.67000,-0.63500),V(42.82800,-22.74500,-0.63500),V(42.67700,-22.79100,-0.63500),V(42.52000,-22.80600,-0.63500),V(42.36300,-22.79100,-0.63500),V(42.21200,-22.74500,-0.63500),V(42.07200,-22.67000,-0.63500),V(41.95000,-22.57000,-0.63500),V(41.85000,-22.44800,-0.63500),V(41.77500,-22.30800,-0.63500),V(41.72900,-22.15700,-0.63500),V(41.71400,-22.00000,-0.63500),V(41.72900,-21.84300,-0.63500),V(41.77500,-21.69200,-0.63500),V(41.85000,-21.55200,-0.63500),V(41.95000,-21.43000,-0.63500),V(42.07200,-21.33000,-0.63500),V(42.21200,-21.25500,-0.63500),V(42.36300,-21.20900,-0.63500),V(42.52000,-21.19400,-0.63500),V(42.67700,-21.20900,-0.63500),V(42.82800,-21.25500,-0.63500),V(42.96800,-21.33000,-0.63500),V(43.09000,-21.43000,-0.63500),V(43.19000,-21.55200,-0.63500),V(43.26500,-21.69200,-0.63500),V(43.31100,-21.84300,-0.63500),V(43.32600,-22.00000,-0.63500),V(43.31100,-22.15700,-0.63500),V(43.26500,-22.30800,-0.63500),V(43.19000,-22.44800,-0.63500),V(43.09000,-22.57000,-0.63500),V(42.96800,-22.67000,-0.63500)])]).extrude(V(0,0,0.79700)))
_s.append(Part.Face([_poly([V(45.50800,-22.67000,-0.63500),V(45.36800,-22.74500,-0.63500),V(45.21700,-22.79100,-0.63500),V(45.06000,-22.80600,-0.63500),V(44.90300,-22.79100,-0.63500),V(44.75200,-22.74500,-0.63500),V(44.61200,-22.67000,-0.63500),V(44.49000,-22.57000,-0.63500),V(44.39000,-22.44800,-0.63500),V(44.31500,-22.30800,-0.63500),V(44.26900,-22.15700,-0.63500),V(44.25400,-22.00000,-0.63500),V(44.26900,-21.84300,-0.63500),V(44.31500,-21.69200,-0.63500),V(44.39000,-21.55200,-0.63500),V(44.49000,-21.43000,-0.63500),V(44.61200,-21.33000,-0.63500),V(44.75200,-21.25500,-0.63500),V(44.90300,-21.20900,-0.63500),V(45.06000,-21.19400,-0.63500),V(45.21700,-21.20900,-0.63500),V(45.36800,-21.25500,-0.63500),V(45.50800,-21.33000,-0.63500),V(45.63000,-21.43000,-0.63500),V(45.73000,-21.55200,-0.63500),V(45.80500,-21.69200,-0.63500),V(45.85100,-21.84300,-0.63500),V(45.86600,-22.00000,-0.63500),V(45.85100,-22.15700,-0.63500),V(45.80500,-22.30800,-0.63500),V(45.73000,-22.44800,-0.63500),V(45.63000,-22.57000,-0.63500),V(45.50800,-22.67000,-0.63500)])]).extrude(V(0,0,0.79700)))
_s.append(Part.Face([_poly([V(27.72800,-1.81000,-0.63500),V(27.58800,-1.88500,-0.63500),V(27.43700,-1.93100,-0.63500),V(27.28000,-1.94600,-0.63500),V(27.12300,-1.93100,-0.63500),V(26.97200,-1.88500,-0.63500),V(26.83200,-1.81000,-0.63500),V(26.71000,-1.71000,-0.63500),V(26.61000,-1.58800,-0.63500),V(26.53500,-1.44800,-0.63500),V(26.48900,-1.29700,-0.63500),V(26.47400,-1.14000,-0.63500),V(26.48900,-0.98300,-0.63500),V(26.53500,-0.83200,-0.63500),V(26.61000,-0.69200,-0.63500),V(26.71000,-0.57000,-0.63500),V(26.83200,-0.47000,-0.63500),V(26.97200,-0.39500,-0.63500),V(27.12300,-0.34900,-0.63500),V(27.28000,-0.33400,-0.63500),V(27.43700,-0.34900,-0.63500),V(27.58800,-0.39500,-0.63500),V(27.72800,-0.47000,-0.63500),V(27.85000,-0.57000,-0.63500),V(27.95000,-0.69200,-0.63500),V(28.02500,-0.83200,-0.63500),V(28.07100,-0.98300,-0.63500),V(28.08600,-1.14000,-0.63500),V(28.07100,-1.29700,-0.63500),V(28.02500,-1.44800,-0.63500),V(27.95000,-1.58800,-0.63500),V(27.85000,-1.71000,-0.63500),V(27.72800,-1.81000,-0.63500)])]).extrude(V(0,0,0.79700)))
_s.append(Part.Face([_poly([V(30.26800,-1.81000,-0.63500),V(30.12800,-1.88500,-0.63500),V(29.97700,-1.93100,-0.63500),V(29.82000,-1.94600,-0.63500),V(29.66300,-1.93100,-0.63500),V(29.51200,-1.88500,-0.63500),V(29.37200,-1.81000,-0.63500),V(29.25000,-1.71000,-0.63500),V(29.15000,-1.58800,-0.63500),V(29.07500,-1.44800,-0.63500),V(29.02900,-1.29700,-0.63500),V(29.01400,-1.14000,-0.63500),V(29.02900,-0.98300,-0.63500),V(29.07500,-0.83200,-0.63500),V(29.15000,-0.69200,-0.63500),V(29.25000,-0.57000,-0.63500),V(29.37200,-0.47000,-0.63500),V(29.51200,-0.39500,-0.63500),V(29.66300,-0.34900,-0.63500),V(29.82000,-0.33400,-0.63500),V(29.97700,-0.34900,-0.63500),V(30.12800,-0.39500,-0.63500),V(30.26800,-0.47000,-0.63500),V(30.39000,-0.57000,-0.63500),V(30.49000,-0.69200,-0.63500),V(30.56500,-0.83200,-0.63500),V(30.61100,-0.98300,-0.63500),V(30.62600,-1.14000,-0.63500),V(30.61100,-1.29700,-0.63500),V(30.56500,-1.44800,-0.63500),V(30.49000,-1.58800,-0.63500),V(30.39000,-1.71000,-0.63500),V(30.26800,-1.81000,-0.63500)])]).extrude(V(0,0,0.79700)))
_s.append(Part.Face([_poly([V(32.80800,-1.81000,-0.63500),V(32.66800,-1.88500,-0.63500),V(32.51700,-1.93100,-0.63500),V(32.36000,-1.94600,-0.63500),V(32.20300,-1.93100,-0.63500),V(32.05200,-1.88500,-0.63500),V(31.91200,-1.81000,-0.63500),V(31.79000,-1.71000,-0.63500),V(31.69000,-1.58800,-0.63500),V(31.61500,-1.44800,-0.63500),V(31.56900,-1.29700,-0.63500),V(31.55400,-1.14000,-0.63500),V(31.56900,-0.98300,-0.63500),V(31.61500,-0.83200,-0.63500),V(31.69000,-0.69200,-0.63500),V(31.79000,-0.57000,-0.63500),V(31.91200,-0.47000,-0.63500),V(32.05200,-0.39500,-0.63500),V(32.20300,-0.34900,-0.63500),V(32.36000,-0.33400,-0.63500),V(32.51700,-0.34900,-0.63500),V(32.66800,-0.39500,-0.63500),V(32.80800,-0.47000,-0.63500),V(32.93000,-0.57000,-0.63500),V(33.03000,-0.69200,-0.63500),V(33.10500,-0.83200,-0.63500),V(33.15100,-0.98300,-0.63500),V(33.16600,-1.14000,-0.63500),V(33.15100,-1.29700,-0.63500),V(33.10500,-1.44800,-0.63500),V(33.03000,-1.58800,-0.63500),V(32.93000,-1.71000,-0.63500),V(32.80800,-1.81000,-0.63500)])]).extrude(V(0,0,0.79700)))
_s.append(Part.Face([_poly([V(35.34800,-1.81000,-0.63500),V(35.20800,-1.88500,-0.63500),V(35.05700,-1.93100,-0.63500),V(34.90000,-1.94600,-0.63500),V(34.74300,-1.93100,-0.63500),V(34.59200,-1.88500,-0.63500),V(34.45200,-1.81000,-0.63500),V(34.33000,-1.71000,-0.63500),V(34.23000,-1.58800,-0.63500),V(34.15500,-1.44800,-0.63500),V(34.10900,-1.29700,-0.63500),V(34.09400,-1.14000,-0.63500),V(34.10900,-0.98300,-0.63500),V(34.15500,-0.83200,-0.63500),V(34.23000,-0.69200,-0.63500),V(34.33000,-0.57000,-0.63500),V(34.45200,-0.47000,-0.63500),V(34.59200,-0.39500,-0.63500),V(34.74300,-0.34900,-0.63500),V(34.90000,-0.33400,-0.63500),V(35.05700,-0.34900,-0.63500),V(35.20800,-0.39500,-0.63500),V(35.34800,-0.47000,-0.63500),V(35.47000,-0.57000,-0.63500),V(35.57000,-0.69200,-0.63500),V(35.64500,-0.83200,-0.63500),V(35.69100,-0.98300,-0.63500),V(35.70600,-1.14000,-0.63500),V(35.69100,-1.29700,-0.63500),V(35.64500,-1.44800,-0.63500),V(35.57000,-1.58800,-0.63500),V(35.47000,-1.71000,-0.63500),V(35.34800,-1.81000,-0.63500)])]).extrude(V(0,0,0.79700)))
_s.append(Part.Face([_poly([V(37.88800,-1.81000,-0.63500),V(37.74800,-1.88500,-0.63500),V(37.59700,-1.93100,-0.63500),V(37.44000,-1.94600,-0.63500),V(37.28300,-1.93100,-0.63500),V(37.13200,-1.88500,-0.63500),V(36.99200,-1.81000,-0.63500),V(36.87000,-1.71000,-0.63500),V(36.77000,-1.58800,-0.63500),V(36.69500,-1.44800,-0.63500),V(36.64900,-1.29700,-0.63500),V(36.63400,-1.14000,-0.63500),V(36.64900,-0.98300,-0.63500),V(36.69500,-0.83200,-0.63500),V(36.77000,-0.69200,-0.63500),V(36.87000,-0.57000,-0.63500),V(36.99200,-0.47000,-0.63500),V(37.13200,-0.39500,-0.63500),V(37.28300,-0.34900,-0.63500),V(37.44000,-0.33400,-0.63500),V(37.59700,-0.34900,-0.63500),V(37.74800,-0.39500,-0.63500),V(37.88800,-0.47000,-0.63500),V(38.01000,-0.57000,-0.63500),V(38.11000,-0.69200,-0.63500),V(38.18500,-0.83200,-0.63500),V(38.23100,-0.98300,-0.63500),V(38.24600,-1.14000,-0.63500),V(38.23100,-1.29700,-0.63500),V(38.18500,-1.44800,-0.63500),V(38.11000,-1.58800,-0.63500),V(38.01000,-1.71000,-0.63500),V(37.88800,-1.81000,-0.63500)])]).extrude(V(0,0,0.79700)))
_s.append(Part.Face([_poly([V(40.42800,-1.81000,-0.63500),V(40.28800,-1.88500,-0.63500),V(40.13700,-1.93100,-0.63500),V(39.98000,-1.94600,-0.63500),V(39.82300,-1.93100,-0.63500),V(39.67200,-1.88500,-0.63500),V(39.53200,-1.81000,-0.63500),V(39.41000,-1.71000,-0.63500),V(39.31000,-1.58800,-0.63500),V(39.23500,-1.44800,-0.63500),V(39.18900,-1.29700,-0.63500),V(39.17400,-1.14000,-0.63500),V(39.18900,-0.98300,-0.63500),V(39.23500,-0.83200,-0.63500),V(39.31000,-0.69200,-0.63500),V(39.41000,-0.57000,-0.63500),V(39.53200,-0.47000,-0.63500),V(39.67200,-0.39500,-0.63500),V(39.82300,-0.34900,-0.63500),V(39.98000,-0.33400,-0.63500),V(40.13700,-0.34900,-0.63500),V(40.28800,-0.39500,-0.63500),V(40.42800,-0.47000,-0.63500),V(40.55000,-0.57000,-0.63500),V(40.65000,-0.69200,-0.63500),V(40.72500,-0.83200,-0.63500),V(40.77100,-0.98300,-0.63500),V(40.78600,-1.14000,-0.63500),V(40.77100,-1.29700,-0.63500),V(40.72500,-1.44800,-0.63500),V(40.65000,-1.58800,-0.63500),V(40.55000,-1.71000,-0.63500),V(40.42800,-1.81000,-0.63500)])]).extrude(V(0,0,0.79700)))
_s.append(Part.Face([_poly([V(42.96800,-1.81000,-0.63500),V(42.82800,-1.88500,-0.63500),V(42.67700,-1.93100,-0.63500),V(42.52000,-1.94600,-0.63500),V(42.36300,-1.93100,-0.63500),V(42.21200,-1.88500,-0.63500),V(42.07200,-1.81000,-0.63500),V(41.95000,-1.71000,-0.63500),V(41.85000,-1.58800,-0.63500),V(41.77500,-1.44800,-0.63500),V(41.72900,-1.29700,-0.63500),V(41.71400,-1.14000,-0.63500),V(41.72900,-0.98300,-0.63500),V(41.77500,-0.83200,-0.63500),V(41.85000,-0.69200,-0.63500),V(41.95000,-0.57000,-0.63500),V(42.07200,-0.47000,-0.63500),V(42.21200,-0.39500,-0.63500),V(42.36300,-0.34900,-0.63500),V(42.52000,-0.33400,-0.63500),V(42.67700,-0.34900,-0.63500),V(42.82800,-0.39500,-0.63500),V(42.96800,-0.47000,-0.63500),V(43.09000,-0.57000,-0.63500),V(43.19000,-0.69200,-0.63500),V(43.26500,-0.83200,-0.63500),V(43.31100,-0.98300,-0.63500),V(43.32600,-1.14000,-0.63500),V(43.31100,-1.29700,-0.63500),V(43.26500,-1.44800,-0.63500),V(43.19000,-1.58800,-0.63500),V(43.09000,-1.71000,-0.63500),V(42.96800,-1.81000,-0.63500)])]).extrude(V(0,0,0.79700)))
_s.append(Part.Face([_poly([V(45.50800,-1.81000,-0.63500),V(45.36800,-1.88500,-0.63500),V(45.21700,-1.93100,-0.63500),V(45.06000,-1.94600,-0.63500),V(44.90300,-1.93100,-0.63500),V(44.75200,-1.88500,-0.63500),V(44.61200,-1.81000,-0.63500),V(44.49000,-1.71000,-0.63500),V(44.39000,-1.58800,-0.63500),V(44.31500,-1.44800,-0.63500),V(44.26900,-1.29700,-0.63500),V(44.25400,-1.14000,-0.63500),V(44.26900,-0.98300,-0.63500),V(44.31500,-0.83200,-0.63500),V(44.39000,-0.69200,-0.63500),V(44.49000,-0.57000,-0.63500),V(44.61200,-0.47000,-0.63500),V(44.75200,-0.39500,-0.63500),V(44.90300,-0.34900,-0.63500),V(45.06000,-0.33400,-0.63500),V(45.21700,-0.34900,-0.63500),V(45.36800,-0.39500,-0.63500),V(45.50800,-0.47000,-0.63500),V(45.63000,-0.57000,-0.63500),V(45.73000,-0.69200,-0.63500),V(45.80500,-0.83200,-0.63500),V(45.85100,-0.98300,-0.63500),V(45.86600,-1.14000,-0.63500),V(45.85100,-1.29700,-0.63500),V(45.80500,-1.44800,-0.63500),V(45.73000,-1.58800,-0.63500),V(45.63000,-1.71000,-0.63500),V(45.50800,-1.81000,-0.63500)])]).extrude(V(0,0,0.79700)))
_add('L49' + '_L49', _fuse(_s), (0.2353,0.7059,0.2941), surface=True)
# --- substrate (layers [57]) : z -0.6350..0 mm ---
_s = []
_s.append(Part.Face([_poly([V(45.80000,-3.20000,-0.63500),V(45.80000,-20.10000,-0.63500),V(8.90000,-20.10000,-0.63500),V(8.90000,-3.20000,-0.63500),V(45.80000,-3.20000,-0.63500)])]).extrude(V(0,0,0.63500)))
_add('Substrate', _fuse(_s), (0.97, 0.97, 0.95), surface=True)
# --- component 30_PIN_pkg (model) ---
try:
    _place_model('C:/step_models/kovar_dip/KOVAR_DIP30_0.9in.step', '30_PIN_pkg_1', 9.40000, -22.20000, -0.63500, 0.0000, False)
except Exception as _e:
    App.Console.PrintWarning('HLayout: could not read KOVAR_DIP30_0.9in.step for 30_PIN_pkg: %s\n' % _e)
# --- component CAP_1210 (model) ---
try:
    _place_model('C:/step_models/CAP_1210.step', 'C1_CAP_1210', 9.97000, -15.05000, 0.04200, 270.0000, False)
except Exception as _e:
    App.Console.PrintWarning('HLayout: could not read CAP_1210.step for CAP_1210: %s\n' % _e)
# --- component CAP_1210 (model) ---
try:
    _place_model('C:/step_models/CAP_1210.step', 'C2_CAP_1210', 29.12000, -15.45000, 0.04200, 180.0000, False)
except Exception as _e:
    App.Console.PrintWarning('HLayout: could not read CAP_1210.step for CAP_1210: %s\n' % _e)
# --- component CAP_1210 (model) ---
try:
    _place_model('C:/step_models/CAP_1210.step', 'C3_CAP_1210', 17.92000, -5.25000, 0.04200, 270.0000, False)
except Exception as _e:
    App.Console.PrintWarning('HLayout: could not read CAP_1210.step for CAP_1210: %s\n' % _e)
# --- component CAP_1210 (model) ---
try:
    _place_model('C:/step_models/CAP_1210.step', 'C4_CAP_1210', 16.17000, -8.10000, 0.04200, 90.0000, False)
except Exception as _e:
    App.Console.PrintWarning('HLayout: could not read CAP_1210.step for CAP_1210: %s\n' % _e)
# --- component CAP_0805 (model) ---
try:
    _place_model('C:/step_models/CAP_0805.step', 'C5_CAP_0805', 22.27000, -6.00000, 0.04200, 270.0000, False)
except Exception as _e:
    App.Console.PrintWarning('HLayout: could not read CAP_0805.step for CAP_0805: %s\n' % _e)
# --- component CAP_0805 (model) ---
try:
    _place_model('C:/step_models/CAP_0805.step', 'C6_CAP_0805', 44.27000, -7.20000, 0.04200, 90.0000, False)
except Exception as _e:
    App.Console.PrintWarning('HLayout: could not read CAP_0805.step for CAP_0805: %s\n' % _e)
# --- component CAP_0805 (model) ---
try:
    _place_model('C:/step_models/CAP_0805.step', 'C8_CAP_0805', 42.32000, -14.45000, 0.04200, 90.0000, False)
except Exception as _e:
    App.Console.PrintWarning('HLayout: could not read CAP_0805.step for CAP_0805: %s\n' % _e)
# --- component CAP_0805 (model) ---
try:
    _place_model('C:/step_models/CAP_0805.step', 'C9_CAP_0805', 35.27000, -10.25000, 0.04200, 270.0000, False)
except Exception as _e:
    App.Console.PrintWarning('HLayout: could not read CAP_0805.step for CAP_0805: %s\n' % _e)
# --- component CAP_0805 (model) ---
try:
    _place_model('C:/step_models/CAP_0805.step', 'C10_CAP_0805', 38.57000, -12.50000, 0.04200, 270.0000, False)
except Exception as _e:
    App.Console.PrintWarning('HLayout: could not read CAP_0805.step for CAP_0805: %s\n' % _e)
# --- component CAP_0805 (model) ---
try:
    _place_model('C:/step_models/CAP_0805.step', 'C11_CAP_0805', 44.52000, -9.95000, 0.04200, 90.0000, False)
except Exception as _e:
    App.Console.PrintWarning('HLayout: could not read CAP_0805.step for CAP_0805: %s\n' % _e)
# --- component CAP_0805 (model) ---
try:
    _place_model('C:/step_models/CAP_0805.step', 'C12_CAP_0805', 39.77000, -17.80000, 0.04200, 90.0000, False)
except Exception as _e:
    App.Console.PrintWarning('HLayout: could not read CAP_0805.step for CAP_0805: %s\n' % _e)
# --- component CAP_0805 (model) ---
try:
    _place_model('C:/step_models/CAP_0805.step', 'C13_CAP_0805', 38.62000, -6.70000, 0.04200, 90.0000, False)
except Exception as _e:
    App.Console.PrintWarning('HLayout: could not read CAP_0805.step for CAP_0805: %s\n' % _e)
# --- component CAP_1210 (model) ---
try:
    _place_model('C:/step_models/CAP_1210.step', 'C15_CAP_1210', 12.57000, -8.15000, 0.04200, 90.0000, False)
except Exception as _e:
    App.Console.PrintWarning('HLayout: could not read CAP_1210.step for CAP_1210: %s\n' % _e)
# --- component CAP_1210 (model) ---
try:
    _place_model('C:/step_models/CAP_1210.step', 'C16_CAP_1210', 23.62000, -18.65000, 0.04200, 90.0000, False)
except Exception as _e:
    App.Console.PrintWarning('HLayout: could not read CAP_1210.step for CAP_1210: %s\n' % _e)
# --- component CAP_0805 (model) ---
try:
    _place_model('C:/step_models/CAP_0805.step', 'C17_CAP_0805', 20.77000, -9.35000, 0.04200, 180.0000, False)
except Exception as _e:
    App.Console.PrintWarning('HLayout: could not read CAP_0805.step for CAP_0805: %s\n' % _e)
# --- component ZENER_5V1 (extrude 1.0000 mm) ---
_sh = Part.Face(_poly([V(36.77000,-8.30000,0.00000),V(36.27000,-8.30000,0.00000),V(36.27000,-8.80000,0.00000),V(36.77000,-8.80000,0.00000),V(36.77000,-8.30000,0.00000)])).extrude(V(0,0,1.00000))
_sh.translate(V(0, 0, 0.04200))
_add('D1_ZENER_5V1', _sh, (0.15,0.15,0.17))
# --- component OP249 (extrude 1.0000 mm) ---
_sh = Part.Face(_poly([V(30.43500,-10.13000,0.00000),V(28.60500,-10.13000,0.00000),V(28.60500,-12.97000,0.00000),V(30.43500,-12.97000,0.00000),V(30.43500,-10.13000,0.00000)])).extrude(V(0,0,1.00000))
_sh.translate(V(0, 0, 0.04200))
_add('U1_OP249', _sh, (0.15,0.15,0.17))
# --- component L_1206_3216Metric (model) ---
try:
    _place_model('C:/step_models/L_1206_3216Metric.step', 'L1_L_1206_3216Metric', 23.67000, -10.00000, 0.04200, 270.0000, False)
except Exception as _e:
    App.Console.PrintWarning('HLayout: could not read L_1206_3216Metric.step for L_1206_3216Metric: %s\n' % _e)
# --- wire bonds (layers [59]) ---
_BONDS = [
    (36.52000, -8.55000, 37.77000, -8.55000, 0.05000),
    (30.28500, -12.55000, 31.80000, -13.10000, 0.05000),
    (30.28500, -11.88300, 32.43000, -11.91700, 0.05000),
    (30.28500, -11.21700, 32.13000, -10.58300, 0.05000),
    (28.75200, -10.65300, 26.89700, -10.60300, 0.05000),
    (28.75500, -11.21700, 27.00000, -11.20000, 0.05000),
    (28.75500, -11.88300, 26.70000, -11.90000, 0.05000),
]
_bw = []
for _x0, _y0, _x1, _y1, _r in _BONDS:
    _z0 = _top_z(_x0, _y0, default=0.0)
    _z1 = _top_z(_x1, _y1, default=0.0)
    _za = max(_z0, _z1) + 0.25000
    _bw.append(_bondwire(V(_x0, _y0, _z0), V((_x0 + _x1) / 2.0, (_y0 + _y1) / 2.0, _za), V(_x1, _y1, _z1), _r))
_add('wire_bonds', _fuse(_bw), (0.8310,0.6860,0.2160))

_doc.recompute()
if _GUI:
    try:
        FreeCADGui.activeDocument().activeView().viewIsometric()
        FreeCADGui.SendMsgToActiveView("ViewFit")
    except Exception:
        pass
