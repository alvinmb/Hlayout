# HLayout - thick-film hybrid circuit layout
# Copyright (C) 2026 Alvin Brown
# SPDX-License-Identifier: GPL-3.0-or-later

"""HLayout-generated FreeCAD macro: builds 3D STEP models for
one of the examples/generate_*.py standalone package scripts,
centred on the origin to match that script's own 2D cells --
see hlayout.io.example_step3d.write_step_macro().

Run: Macro > Macros... > Execute (inside FreeCAD), or
``freecadcmd build_step_models.FCMacro`` from a shell."""
import os
import FreeCAD as App
import Part

V = App.Vector
# this script lives in <HLayout>/build_STEP_parts; the STEP files go to
# <HLayout>/examples/step_models/substrates wherever it is run from
_ROOT = (os.path.dirname(os.path.dirname(os.path.abspath(__file__)))
         if "__file__" in globals() else os.getcwd())
# HLAYOUT_STEP_DIR (set by build_all.py) overrides where the STEP files go
OUT_DIR = os.path.join(os.environ.get("HLAYOUT_STEP_DIR") or os.path.join(_ROOT, "examples", "step_models"), "substrates")
os.makedirs(OUT_DIR, exist_ok=True)


def make_end_cap(L, W, H, term_len, overhang=0.0, over=0.02):
    """A rectangular body with two metallised end terminations, each
    extending `overhang` past the body's own end -- the real
    wraparound solder fillet sticking out beyond the body, matching
    generate_tantalum_capacitors.py's own pad_outer/pad_cx overhang
    math exactly (overhang=0 draws terminations flush with the body
    ends instead). Origin at the BOTTOM-LEFT corner in X/Y (body spans
    (0, 0) to (L, W)), sitting on Z=0 up to Z=H -- long axis along X."""
    body = Part.makeBox(L, W, H, V(-L / 2.0, -W / 2.0, 0))
    pad_outer = L / 2.0 + overhang
    pad_inner = pad_outer - term_len
    term1 = Part.makeBox(term_len, W + 2 * over, H + 2 * over,
                          V(-pad_outer, -W / 2.0 - over, -over))
    term2 = Part.makeBox(term_len, W + 2 * over, H + 2 * over,
                          V(pad_inner, -W / 2.0 - over, -over))
    shape = Part.makeCompound([body, term1, term2])
    shape.translate(V(L / 2.0, W / 2.0, 0))
    return shape


def make_lcc(side, pitch, per_side, pad_w, pad_depth, H):
    """A square leadless chip carrier: a body with castellated pads
    straddling all four edges, full-height (Z=0 to H) the way a real
    castellation plates the fired side of the part. Origin at the
    BOTTOM-LEFT corner in X/Y (body spans (0, 0) to (side, side)),
    matching generate_lcc_packages.py's own bottom-left cell origin
    (see that script for the pin-1-bottom-left, counterclockwise
    numbering this follows)."""
    half = side / 2.0
    shapes = [Part.makeBox(side, side, H, V(-half, -half, 0))]
    span = (per_side - 1) * pitch
    xs = [(-span / 2.0) + k * pitch for k in range(per_side)]

    def _pad(cx, cy, horizontal):
        if horizontal:
            return Part.makeBox(pad_w, pad_depth, H, V(cx - pad_w / 2.0, cy - pad_depth / 2.0, 0))
        return Part.makeBox(pad_depth, pad_w, H, V(cx - pad_depth / 2.0, cy - pad_w / 2.0, 0))

    for x in xs:
        shapes.append(_pad(x, -half, True))
    for y in xs:
        shapes.append(_pad(half, y, False))
    for x in reversed(xs):
        shapes.append(_pad(x, half, True))
    for y in reversed(xs):
        shapes.append(_pad(-half, y, False))
    shape = Part.makeCompound(shapes)
    shape.translate(V(half, half, 0))
    return shape


def make_substrate_pins(L, W, H, per_side, pitch, pad_dia, pin_length):
    """A dual-row ceramic substrate: a body with round pads on its two
    long edges. pin_length > 0 draws each pad as a cylindrical pin
    running from pin_length below Z=0 up through the body to Z=H (a
    braze feedthrough pin, the _HOLE variant); pin_length == 0 draws a
    thin round surface pad instead (no protruding pin). Origin at the
    BOTTOM-LEFT corner in X/Y (body spans (0, 0) to (L, W)), matching
    generate_ceramic_substrates.py's own bottom-left cell origin."""
    half_l, half_w = L / 2.0, W / 2.0
    shapes = [Part.makeBox(L, W, H, V(-half_l, -half_w, 0))]
    span = (per_side - 1) * pitch
    xs = [(-span / 2.0) + k * pitch for k in range(per_side)]
    r = pad_dia / 2.0
    for x in xs:
        for y in (-half_w, half_w):
            if pin_length > 0:
                shapes.append(Part.makeCylinder(r, H + pin_length, V(x, y, -pin_length)))
            else:
                pad_h = max(H * 0.1, 0.05)
                shapes.append(Part.makeCylinder(r, pad_h, V(x, y, H - pad_h)))
    shape = Part.makeCompound(shapes)
    shape.translate(V(half_l, half_w, 0))
    return shape


def _gullwing_side(y_wall, y_dir, leads, lead_out, lead_t, lead_mid_z, lead_foot):
    """leads: list of (x, lead_w). One stub/drop/foot triple per lead."""
    shapes = []
    for x, lead_w in leads:
        y_outer = y_wall + y_dir * lead_out
        stub_y0 = min(y_wall, y_outer)
        stub_y1 = max(y_wall, y_outer)
        shapes.append(Part.makeBox(lead_w, stub_y1 - stub_y0, lead_t,
                                    V(x - lead_w / 2.0, stub_y0, lead_mid_z - lead_t / 2.0)))
        drop_y0 = min(y_outer, y_outer + y_dir * lead_t)
        drop_y1 = max(y_outer, y_outer + y_dir * lead_t)
        shapes.append(Part.makeBox(lead_w, drop_y1 - drop_y0, lead_mid_z + lead_t / 2.0,
                                    V(x - lead_w / 2.0, drop_y0, 0)))
        y_tip = y_outer + y_dir * lead_foot
        foot_y0 = min(y_outer, y_tip)
        foot_y1 = max(y_outer, y_tip)
        shapes.append(Part.makeBox(lead_w, foot_y1 - foot_y0, lead_t,
                                    V(x - lead_w / 2.0, foot_y0, 0)))
    return shapes


def make_dip(L, W, H, leads_neg_y, leads_pos_y, lead_t, lead_out, lead_foot, lid=None):
    """A dual-row gull-wing package with its two rows along Y (at
    Y=0 and Y=W) and pins spread along X within each row -- covers a
    Kyocera-style CFP (lid=(lid_margin, lid_height); see
    generate_kyocera_cfp_packages.py, whose own 2D convention runs
    this same way). Origin at the BOTTOM-LEFT corner in X/Y (body
    spans (0, 0) to (L, W)), sitting on Z=0."""
    shapes = [Part.makeBox(L, W, H, V(-L / 2.0, -W / 2.0, 0))]
    lead_mid_z = H * 0.5
    shapes.extend(_gullwing_side(-W / 2.0, -1, leads_neg_y, lead_out, lead_t, lead_mid_z, lead_foot))
    shapes.extend(_gullwing_side(W / 2.0, 1, leads_pos_y, lead_out, lead_t, lead_mid_z, lead_foot))
    if lid is not None:
        lid_margin, lid_h = lid
        shapes.append(Part.makeBox(L - 2 * lid_margin, W - 2 * lid_margin, lid_h,
                                    V(-L / 2.0 + lid_margin, -W / 2.0 + lid_margin, H)))
    shape = Part.makeCompound(shapes)
    shape.translate(V(L / 2.0, W / 2.0, 0))
    return shape


def _gullwing_side_x(x_wall, x_dir, leads, lead_out, lead_t, lead_mid_z, lead_foot):
    """The _gullwing_side() twin for a package whose two rows run
    along X instead of Y -- leads: list of (y, lead_w)."""
    shapes = []
    for y, lead_w in leads:
        x_outer = x_wall + x_dir * lead_out
        stub_x0 = min(x_wall, x_outer)
        stub_x1 = max(x_wall, x_outer)
        shapes.append(Part.makeBox(stub_x1 - stub_x0, lead_w, lead_t,
                                    V(stub_x0, y - lead_w / 2.0, lead_mid_z - lead_t / 2.0)))
        drop_x0 = min(x_outer, x_outer + x_dir * lead_t)
        drop_x1 = max(x_outer, x_outer + x_dir * lead_t)
        shapes.append(Part.makeBox(drop_x1 - drop_x0, lead_w, lead_mid_z + lead_t / 2.0,
                                    V(drop_x0, y - lead_w / 2.0, 0)))
        x_tip = x_outer + x_dir * lead_foot
        foot_x0 = min(x_outer, x_tip)
        foot_x1 = max(x_outer, x_tip)
        shapes.append(Part.makeBox(foot_x1 - foot_x0, lead_w, lead_t,
                                    V(foot_x0, y - lead_w / 2.0, 0)))
    return shapes


def make_dip_x(L, W, H, leads_neg_x, leads_pos_x, lead_t, lead_out, lead_foot):
    """The make_dip() twin for a package whose two rows run along X
    instead of Y (at X=0 and X=L), pins spread along Y within each
    row -- matches generate_sot_packages.py's own 2D convention (see
    that script's build_package() for why rows run along X there).
    Origin at the BOTTOM-LEFT corner in X/Y (body spans (0, 0) to
    (L, W)), sitting on Z=0."""
    shapes = [Part.makeBox(L, W, H, V(-L / 2.0, -W / 2.0, 0))]
    lead_mid_z = H * 0.5
    shapes.extend(_gullwing_side_x(-L / 2.0, -1, leads_neg_x, lead_out, lead_t, lead_mid_z, lead_foot))
    shapes.extend(_gullwing_side_x(L / 2.0, 1, leads_pos_x, lead_out, lead_t, lead_mid_z, lead_foot))
    shape = Part.makeCompound(shapes)
    shape.translate(V(L / 2.0, W / 2.0, 0))
    return shape


def export(shape, name, out_dir):
    path = os.path.join(out_dir, name + ".step")
    if os.path.isfile(path):
        App.Console.PrintMessage("HLayout: %s already exists, leaving it alone\n" % path)
        return
    shape.exportStep(path)
    App.Console.PrintMessage("HLayout: wrote %s (%d solids)\n" % (path, len(shape.Solids)))


_doc = App.newDocument("HLayoutStepModels")

export(make_substrate_pins(L=26.86, W=10.0, H=1.5, per_side=10, pitch=2.54, pad_dia=1.5, pin_length=0.0), 'SUBSTRATE-20', OUT_DIR)
export(make_substrate_pins(L=26.86, W=10.0, H=1.5, per_side=10, pitch=2.54, pad_dia=1.5, pin_length=2.0), 'SUBSTRATE-20-HOLE', OUT_DIR)
export(make_substrate_pins(L=39.56, W=10.0, H=1.5, per_side=15, pitch=2.54, pad_dia=1.5, pin_length=0.0), 'SUBSTRATE-30', OUT_DIR)
export(make_substrate_pins(L=39.56, W=10.0, H=1.5, per_side=15, pitch=2.54, pad_dia=1.5, pin_length=2.0), 'SUBSTRATE-30-HOLE', OUT_DIR)
export(make_substrate_pins(L=52.26, W=10.0, H=1.5, per_side=20, pitch=2.54, pad_dia=1.5, pin_length=0.0), 'SUBSTRATE-40', OUT_DIR)
export(make_substrate_pins(L=52.26, W=10.0, H=1.5, per_side=20, pitch=2.54, pad_dia=1.5, pin_length=2.0), 'SUBSTRATE-40-HOLE', OUT_DIR)
App.Console.PrintMessage("HLayout: STEP model build complete.\n")
