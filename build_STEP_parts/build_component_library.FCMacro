# HLayout - thick-film hybrid circuit layout
# Copyright (C) 2026 Alvin Brown
# SPDX-License-Identifier: GPL-3.0-or-later

"""HLayout-generated FreeCAD macro: builds a small 3D component
library (generic ceramic chip capacitors, a 20-pin sealed
metal/ceramic hybrid flatpack, the SOT small-outline-
transistor gull-wing package family, and the ceramic LCC /
plastic PLCC chip-carrier families) and exports each as its
own STEP file, ready to be referenced from Setup > Technology
Properties..."s Resistors/component_models "model" mode -- see
hlayout.io.component_library.write_component_library_macro().

Run: Macro > Macros... > Execute (inside FreeCAD), or
``freecadcmd build_component_library.FCMacro`` from a shell."""
import os
import FreeCAD as App
import Part

V = App.Vector
_ROOT = (os.path.dirname(os.path.dirname(os.path.abspath(__file__)))
         if "__file__" in globals() else os.getcwd())
# HLAYOUT_STEP_DIR (set by build_all.py) overrides where the STEP files go
OUT_DIR = os.environ.get("HLAYOUT_STEP_DIR") or os.path.join(_ROOT, "examples", "step_models")
os.makedirs(OUT_DIR, exist_ok=True)


def make_ceramic_cap(L, W, H, term_len, over=0.02):
    """A rectangular ceramic chip capacitor body with two metallised end
    terminations. Origin at the bottom-left corner in X/Y (body spans
    (0, 0) to (L, W)), sitting on Z=0 (the substrate surface) up to
    Z=H -- long axis along X."""
    body = Part.makeBox(L, W, H, V(-L / 2.0, -W / 2.0, 0))
    term1 = Part.makeBox(term_len, W + 2 * over, H + 2 * over,
                          V(-L / 2.0, -W / 2.0 - over, -over))
    term2 = Part.makeBox(term_len, W + 2 * over, H + 2 * over,
                          V(L / 2.0 - term_len, -W / 2.0 - over, -over))
    shape = Part.makeCompound([body, term1, term2])
    shape.translate(V(L / 2.0, W / 2.0, 0))
    return shape


def make_pkg20(L, W, H_body, H_lid, lid_margin, n_per_side, pitch,
               lead_w, lead_t, lead_out, lead_foot):
    """A sealed metal/ceramic 20-pin hybrid flatpack: a rectangular base
    with an inset lid, and n_per_side gull-wing leads per long side.
    Origin at the bottom-left corner in X/Y (body spans (0, 0) to
    (L, W)), sitting on Z=0 -- each lead's foot rests on Z=0 for a
    realistic seated placement."""
    shapes = [
        Part.makeBox(L, W, H_body, V(-L / 2.0, -W / 2.0, 0)),
        Part.makeBox(L - 2 * lid_margin, W - 2 * lid_margin, H_lid,
                      V(-L / 2.0 + lid_margin, -W / 2.0 + lid_margin, H_body)),
    ]

    span = (n_per_side - 1) * pitch
    x0 = -span / 2.0
    lead_mid_z = H_body * 0.5

    for i in range(n_per_side):
        x = x0 + i * pitch
        for y_wall, y_dir in ((W / 2.0, 1), (-W / 2.0, -1)):
            y_outer = y_wall + y_dir * lead_out
            # 1) stub: horizontal, from the body wall out to y_outer
            stub_y0 = min(y_wall, y_outer)
            stub_y1 = max(y_wall, y_outer)
            shapes.append(Part.makeBox(lead_w, stub_y1 - stub_y0, lead_t,
                                        V(x - lead_w / 2.0, stub_y0, lead_mid_z - lead_t / 2.0)))
            # 2) drop: vertical, at y_outer, from the substrate up to the stub
            drop_y0 = min(y_outer, y_outer + y_dir * lead_t)
            drop_y1 = max(y_outer, y_outer + y_dir * lead_t)
            shapes.append(Part.makeBox(lead_w, drop_y1 - drop_y0, lead_mid_z + lead_t / 2.0,
                                        V(x - lead_w / 2.0, drop_y0, 0)))
            # 3) foot: horizontal, at the substrate, extending further out
            y_tip = y_outer + y_dir * lead_foot
            foot_y0 = min(y_outer, y_tip)
            foot_y1 = max(y_outer, y_tip)
            shapes.append(Part.makeBox(lead_w, foot_y1 - foot_y0, lead_t,
                                        V(x - lead_w / 2.0, foot_y0, 0)))

    shape = Part.makeCompound(shapes)
    shape.translate(V(L / 2.0, W / 2.0, 0))
    return shape


def _gullwing_side(y_wall, y_dir, leads, lead_out, lead_t, lead_mid_z, lead_foot):
    """leads: list of (x, lead_w). One stub/drop/foot triple per lead
    -- the same 3-box gull-wing shape make_pkg20 uses, factored out so
    a package can put a different, independent set of leads on each
    side (needed for e.g. SOT-23's 2-leads/1-lead split and SOT-223's
    3 leads + 1 wide tab lead)."""
    shapes = []
    for x, lead_w in leads:
        y_outer = y_wall + y_dir * lead_out
        stub_y0 = min(y_wall, y_outer)
        stub_y1 = max(y_wall, y_outer)
        shapes.append(Part.makeBox(lead_w, stub_y1 - stub_y0, lead_t,
                                    V(x - lead_w / 2.0, stub_y0, lead_mid_z - lead_t / 2.0)))
        drop_y0 = min(y_outer, y_outer + y_dir * lead_t)
        drop_y1 = max(y_outer, y_outer + y_dir * lead_t)
        shapes.append(Part.makeBox(lead_w, drop_y1 - drop_y0, lead_mid_z + lead_t / 2.0,
                                    V(x - lead_w / 2.0, drop_y0, 0)))
        y_tip = y_outer + y_dir * lead_foot
        foot_y0 = min(y_outer, y_tip)
        foot_y1 = max(y_outer, y_tip)
        shapes.append(Part.makeBox(lead_w, foot_y1 - foot_y0, lead_t,
                                    V(x - lead_w / 2.0, foot_y0, 0)))
    return shapes


def make_sot(L, W, H, lead_t, lead_out, lead_foot,
             leads_neg_y=(), leads_pos_y=(), heat_tab=None):
    """A generic small-outline-transistor gull-wing package: a
    rectangular body with independently configurable leads on its -Y
    and +Y sides (each a list of (x_mm, lead_width_mm) pairs) -- covers
    SOT-23/SOT-323's 2-leads/1-lead split and SOT-223's 3 leads + 1
    wide tab lead with the same shape generator. Origin at the
    bottom-left corner in X/Y (body spans (0, 0) to (L, W)), sitting
    on Z=0.

    heat_tab, if given, is (y_dir, tab_width, tab_thickness, overhang)
    for a flat metal area flush with the body's top on the y_dir side
    (SOT-89's heatsink tab) -- physically part of the body, not a
    gull-wing lead."""
    shapes = [Part.makeBox(L, W, H, V(-L / 2.0, -W / 2.0, 0))]
    lead_mid_z = H * 0.5
    shapes.extend(_gullwing_side(-W / 2.0, -1, leads_neg_y, lead_out, lead_t, lead_mid_z, lead_foot))
    shapes.extend(_gullwing_side(W / 2.0, 1, leads_pos_y, lead_out, lead_t, lead_mid_z, lead_foot))
    if heat_tab is not None:
        y_dir, tab_w, tab_t, overhang = heat_tab
        y_wall = y_dir * W / 2.0
        y_outer = y_wall + y_dir * overhang
        y0 = min(y_wall, y_outer)
        y1 = max(y_wall, y_outer)
        shapes.append(Part.makeBox(tab_w, y1 - y0, tab_t, V(-tab_w / 2.0, y0, H - tab_t)))
    shape = Part.makeCompound(shapes)
    shape.translate(V(L / 2.0, W / 2.0, 0))
    return shape


def _side_positions(n_side, pitch):
    span = (n_side - 1) * pitch
    return [-span / 2.0 + i * pitch for i in range(n_side)]


def _four_sides(side_shapes):
    """side_shapes: shapes built for the +Y edge; returns them plus
    copies rotated 90/180/270 degrees about the Z axis through (0, 0)."""
    out = list(side_shapes)
    for ang in (90, 180, 270):
        for s in side_shapes:
            c = s.copy()
            c.rotate(V(0, 0, 0), V(0, 0, 1), ang)
            out.append(c)
    return out


def _pin1_x(n_side, pitch):
    # pin 1 is the top-edge terminal at (or just left of) centre --
    # counter-clockwise numbering starting from the top centre
    return 0.0 if n_side % 2 else -pitch / 2.0


def make_lcc(B, H, n_side, pitch=1.27, term_w=0.64, term_len=1.15,
             term_t=0.05, lid_inset=1.27, lid_t=0.08, cast_r=0.3, plate_t=0.03):
    """A ceramic leadless chip carrier (LCCC): a B x B body, H tall
    (seated), n_side castellated terminals per edge at ``pitch``.
    CENTRED on (0, 0) in X/Y, sitting on Z=0.

    Every terminal is a castellation: a half-round notch of radius
    ``cast_r`` cut into the body edge, full height of the ceramic,
    lined with ``plate_t`` of metal, which joins a ``term_w`` x
    ``term_len`` termination pad on the underside (Z=0..term_t, notched
    the same way so the plating runs straight down into it)."""
    zb = term_t
    hb = H - term_t - lid_t                       # ceramic base height
    xs = _side_positions(n_side, pitch)

    def _side(make):
        return _four_sides([make(x) for x in xs])

    # ceramic body with every castellation notch cut out in one boolean
    body = Part.makeBox(B, B, hb, V(-B / 2.0, -B / 2.0, zb))
    notches = _side(lambda x: Part.makeCylinder(cast_r, hb + 0.2, V(x, B / 2.0, zb - 0.1)))
    body = body.cut(Part.makeCompound(notches))
    shapes = [body]

    lid = B - 2 * lid_inset
    if lid > 0:
        shapes.append(Part.makeBox(lid, lid, lid_t, V(-lid / 2.0, -lid / 2.0, H - lid_t)))

    def plating(x):
        ring = Part.makeCylinder(cast_r + plate_t, hb, V(x, B / 2.0, zb)).cut(
            Part.makeCylinder(cast_r, hb, V(x, B / 2.0, zb)))
        inside = Part.makeBox(2 * (cast_r + plate_t), cast_r + plate_t, hb,
                              V(x - cast_r - plate_t, B / 2.0 - cast_r - plate_t, zb))
        return ring.common(inside)                # the half lining the notch

    def pad(x):
        p = Part.makeBox(term_w, term_len, term_t, V(x - term_w / 2.0, B / 2.0 - term_len, 0))
        return p.cut(Part.makeCylinder(cast_r, term_t, V(x, B / 2.0, 0)))

    shapes.extend(_side(plating))
    shapes.extend(_side(pad))
    rim = min(lid_inset, 1.0) / 2.0
    shapes.append(Part.makeCylinder(min(0.3, rim), 0.03,
                                    V(_pin1_x(n_side, pitch), B / 2.0 - rim, H - lid_t)))
    return Part.makeCompound(shapes)


def make_plcc(B, E, H, n_side, pitch=1.27, lead_w=0.43, lead_t=0.2,
              standoff=0.6, tuck=0.5):
    """A plastic J-lead chip carrier (PLCC): a B x B moulded body from
    Z=standoff to H, n_side J-leads per edge whose outer faces lie on
    the E x E overall outline and whose curled feet rest on Z=0 tucked
    ``tuck`` under the body edge. CENTRED on (0, 0) in X/Y."""
    shapes = [Part.makeBox(B, B, H - standoff, V(-B / 2.0, -B / 2.0, standoff))]
    shoulder = standoff + (H - standoff) * 0.4
    y_out = E / 2.0
    side = []
    for x in _side_positions(n_side, pitch):
        x0 = x - lead_w / 2.0
        # shoulder: out of the body wall to the overall outline
        side.append(Part.makeBox(lead_w, y_out - B / 2.0, lead_t,
                                 V(x0, B / 2.0, shoulder - lead_t)))
        # outer vertical run down to the board
        side.append(Part.makeBox(lead_w, lead_t, shoulder,
                                 V(x0, y_out - lead_t, 0)))
        # J foot curling back under the body
        side.append(Part.makeBox(lead_w, y_out - (B / 2.0 - tuck), lead_t,
                                 V(x0, B / 2.0 - tuck, 0)))
    shapes.extend(_four_sides(side))
    shapes.append(Part.makeCylinder(0.5, 0.03,
                                    V(_pin1_x(n_side, pitch), B / 2.0 - 1.2, H)))
    return Part.makeCompound(shapes)


def export(shape, name, out_dir):
    path = os.path.join(out_dir, name + ".step")
    if os.path.isfile(path):
        App.Console.PrintMessage("HLayout: %s already exists, leaving it alone\n" % path)
        return
    shape.exportStep(path)
    App.Console.PrintMessage("HLayout: wrote %s (%d solids)\n" % (path, len(shape.Solids)))


_doc = App.newDocument("HLayoutComponentLibrary")

export(make_ceramic_cap(1.6, 0.8, 0.8, 0.3), 'CAP_0603', OUT_DIR)
export(make_ceramic_cap(2.0, 1.25, 1.25, 0.4), 'CAP_0805', OUT_DIR)
export(make_ceramic_cap(3.2, 1.6, 1.6, 0.5), 'CAP_1206', OUT_DIR)
export(make_ceramic_cap(0.6, 0.3, 0.3, 0.15), 'CAP_0201', OUT_DIR)
export(make_ceramic_cap(1.0, 0.5, 0.5, 0.25), 'CAP_0402', OUT_DIR)
export(make_ceramic_cap(3.2, 2.5, 1.2, 0.6), 'CAP_1210', OUT_DIR)
export(make_ceramic_cap(4.5, 3.2, 1.2, 0.6), 'CAP_1812', OUT_DIR)
export(make_ceramic_cap(5.0, 2.5, 1.2, 0.6), 'CAP_2010', OUT_DIR)
export(make_ceramic_cap(6.4, 3.2, 1.2, 0.6), 'CAP_2512', OUT_DIR)
export(make_pkg20(25.0, 12.0, 2.5, 1.0, 1.0, 10, 1.27, 0.4, 0.15, 1.5, 1.2), 'PKG20', OUT_DIR)
export(make_sot(L=2.9, W=1.3, H=1.1, lead_t=0.1, lead_out=0.4, lead_foot=0.4, leads_neg_y=[(-0.475, 0.4), (0.475, 0.4)], leads_pos_y=[(0.0, 0.4)]), 'SOT_23', OUT_DIR)
export(make_sot(L=2.0, W=1.25, H=0.95, lead_t=0.1, lead_out=0.3, lead_foot=0.3, leads_neg_y=[(-0.325, 0.25), (0.325, 0.25)], leads_pos_y=[(0.0, 0.25)]), 'SOT_323', OUT_DIR)
export(make_sot(L=4.5, W=2.5, H=1.5, lead_t=0.2, lead_out=0.6, lead_foot=0.8, leads_neg_y=[(-1.5, 0.6), (0.0, 0.6), (1.5, 0.6)], leads_pos_y=[], heat_tab=(1, 2.0, 0.3, 1.0)), 'SOT_89', OUT_DIR)
export(make_sot(L=6.5, W=3.5, H=1.6, lead_t=0.25, lead_out=0.8, lead_foot=1.0, leads_neg_y=[(-2.3, 0.5), (0.0, 0.5), (2.3, 0.5)], leads_pos_y=[(0.0, 3.0)]), 'SOT_223', OUT_DIR)
export(make_sot(L=8.65, W=3.9, H=1.75, lead_t=0.2, lead_out=0.4, lead_foot=0.6, leads_neg_y=[(-3.81, 0.4), (-2.54, 0.4), (-1.27, 0.4), (0.0, 0.4), (1.27, 0.4), (2.54, 0.4), (3.81, 0.4)], leads_pos_y=[(-3.81, 0.4), (-2.54, 0.4), (-1.27, 0.4), (0.0, 0.4), (1.27, 0.4), (2.54, 0.4), (3.81, 0.4)]), 'SOT_14', OUT_DIR)
export(make_sot(L=9.9, W=3.9, H=1.75, lead_t=0.2, lead_out=0.4, lead_foot=0.6, leads_neg_y=[(-4.445, 0.4), (-3.175, 0.4), (-1.905, 0.4), (-0.635, 0.4), (0.635, 0.4), (1.905, 0.4), (3.175, 0.4), (4.445, 0.4)], leads_pos_y=[(-4.445, 0.4), (-3.175, 0.4), (-1.905, 0.4), (-0.635, 0.4), (0.635, 0.4), (1.905, 0.4), (3.175, 0.4), (4.445, 0.4)]), 'SOT_16', OUT_DIR)
export(make_sot(L=11.16, W=3.9, H=1.75, lead_t=0.2, lead_out=0.4, lead_foot=0.6, leads_neg_y=[(-5.08, 0.4), (-3.81, 0.4), (-2.54, 0.4), (-1.27, 0.4), (0.0, 0.4), (1.27, 0.4), (2.54, 0.4), (3.81, 0.4), (5.08, 0.4)], leads_pos_y=[(-5.08, 0.4), (-3.81, 0.4), (-2.54, 0.4), (-1.27, 0.4), (0.0, 0.4), (1.27, 0.4), (2.54, 0.4), (3.81, 0.4), (5.08, 0.4)]), 'SOT_18', OUT_DIR)
export(make_lcc(B=8.89, H=1.9, n_side=5, pitch=1.27), 'LCC20', OUT_DIR)
export(make_lcc(B=11.43, H=1.9, n_side=7, pitch=1.27), 'LCC28', OUT_DIR)
export(make_lcc(B=12.7, H=1.9, n_side=8, pitch=1.27), 'LCC32', OUT_DIR)
export(make_lcc(B=16.51, H=2.0, n_side=11, pitch=1.27), 'LCC44', OUT_DIR)
export(make_lcc(B=19.05, H=2.0, n_side=13, pitch=1.27), 'LCC52', OUT_DIR)
export(make_lcc(B=24.13, H=2.3, n_side=17, pitch=1.27), 'LCC68', OUT_DIR)
export(make_lcc(B=29.21, H=2.3, n_side=21, pitch=1.27), 'LCC84', OUT_DIR)
export(make_plcc(B=8.97, E=9.91, H=4.37, n_side=5, pitch=1.27), 'PLCC20', OUT_DIR)
export(make_plcc(B=11.51, E=12.45, H=4.37, n_side=7, pitch=1.27), 'PLCC28', OUT_DIR)
export(make_plcc(B=12.78, E=13.72, H=4.37, n_side=8, pitch=1.27), 'PLCC32', OUT_DIR)
export(make_plcc(B=16.59, E=17.53, H=4.37, n_side=11, pitch=1.27), 'PLCC44', OUT_DIR)
export(make_plcc(B=19.13, E=20.07, H=4.37, n_side=13, pitch=1.27), 'PLCC52', OUT_DIR)
export(make_plcc(B=24.21, E=25.15, H=4.57, n_side=17, pitch=1.27), 'PLCC68', OUT_DIR)
export(make_plcc(B=29.29, E=30.23, H=4.57, n_side=21, pitch=1.27), 'PLCC84', OUT_DIR)
App.Console.PrintMessage("HLayout: component library build complete.\n")
