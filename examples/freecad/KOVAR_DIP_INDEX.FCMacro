# FreeCAD 3D view of KOVAR_DIP  (cell INDEX)
# Generated by HLayout -- run inside FreeCAD: Macro > Macros... > Execute,
# or  freecadcmd this_file.FCMacro
import FreeCAD as App
import Part
from functools import reduce
_GUI = bool(getattr(App, "GuiUp", False))
if _GUI:
    import FreeCADGui

V = App.Vector
_doc = App.newDocument('KOVAR_DIP_INDEX')


def _poly(points):
    return Part.makePolygon(points)


def _fuse(solids):
    # A compound, not a boolean fuse: every layer's polygons were already
    # merged (shapely unary_union) before being written here, so the
    # solids are disjoint and fusing them is pure cost -- a sequential
    # BRep fuse of ~100 many-vertex traces took minutes and looked like
    # a hang. A compound renders, exports and section-probes the same.
    solids = [s for s in solids if s is not None and not s.isNull()]
    if not solids:
        return None
    return solids[0] if len(solids) == 1 else Part.makeCompound(solids)


#: shapes bonds and parts land on: _SURF = films + substrate (what a
#: component sits on), _PROBE = everything solid so far (what a bond
#: end lands on -- die pads, header pins, traces).
_SURF = []
_PROBE = []


def _parts(shape):
    """A shape's individual solids (or the shape itself) -- what the
    probes below test one by one, so their bounding-box prefilter skips
    almost everything instead of sectioning a whole layer compound."""
    try:
        sol = list(shape.Solids)
    except Exception:
        sol = []
    return sol or [shape]


def _add(name, shape, rgb, surface=False, transparency=0):
    if shape is None:
        return None
    o = _doc.addObject("Part::Feature", name)
    o.Shape = shape
    if _GUI and o.ViewObject is not None:
        o.ViewObject.ShapeColor = rgb
        if transparency:
            o.ViewObject.Transparency = int(transparency)
    _PROBE.extend(_parts(o.Shape))
    if surface:
        _SURF.extend(_parts(o.Shape))
    return o


def _top_z(x, y, shapes=None, default=None):
    """Highest solid surface straight below/at (x, y), or `default`."""
    best = None
    for sh in (_PROBE if shapes is None else shapes):
        bb = sh.BoundBox
        if not (bb.XMin - 1e-6 <= x <= bb.XMax + 1e-6 and bb.YMin - 1e-6 <= y <= bb.YMax + 1e-6):
            continue
        try:
            sec = sh.section(Part.makeLine(V(x, y, bb.ZMax + 1.0), V(x, y, bb.ZMin - 1.0)))
        except Exception:
            continue
        for v in sec.Vertexes:
            if best is None or v.Point.z > best:
                best = v.Point.z
    return default if best is None else best


def _surface_z(x0, y0, x1, y1):
    """Where a part with footprint (x0,y0)-(x1,y1) rests: the highest
    film/substrate top under its centre or inset corners (0 if none)."""
    ix, iy = (x1 - x0) * 0.2, (y1 - y0) * 0.2
    pts = [((x0 + x1) / 2.0, (y0 + y1) / 2.0), (x0 + ix, y0 + iy), (x1 - ix, y0 + iy),
           (x1 - ix, y1 - iy), (x0 + ix, y1 - iy)]
    zs = [_top_z(x, y, _SURF) for x, y in pts]
    zs = [z for z in zs if z is not None]
    return max(zs) if zs else 0.0


_MODEL_SHAPES = {}     # path -> shape read once (probing + headless/mirrored use)
_MODEL_TEMPLATES = {}  # path -> first coloured GUI import, re-used via App::Link


def _progress(msg):
    """Report progress and keep the FreeCAD window painting while the
    macro runs -- otherwise a long GUI run looks frozen ("Not
    Responding") although it is still working."""
    App.Console.PrintMessage("HLayout: %s\n" % msg)
    if _GUI:
        try:
            FreeCADGui.updateGui()
        except Exception:
            pass


def _model_shape(path):
    sh = _MODEL_SHAPES.get(path)
    if sh is None:
        sh = Part.Shape()
        sh.read(path)
        _MODEL_SHAPES[path] = sh
    return sh


def _place_model(path, name, x, y, z, rot_deg, mirrored):
    """Bring a STEP/IGES model in at (x, y, z) rotated rot_deg about Z.

    Each file is read ONCE. In the GUI the first instance is imported
    with ImportGui (so the model's own colours survive) into an
    App::Part named `name`; every further instance of the same file is
    an App::Link to that part -- re-importing the STEP per instance was
    what made a GUI run of a populated board take minutes. Headless (or
    mirrored) instances are plain Part::Features sharing one read."""
    _progress("placing %s" % name)
    P = App.Placement(V(x, y, z), App.Rotation(V(0, 0, 1), rot_deg))
    base = _model_shape(path)
    probe = base.copy()
    probe.Placement = P
    if _GUI and not mirrored:
        try:
            tpl = _MODEL_TEMPLATES.get(path)
            if tpl is not None:
                link = _doc.addObject("App::Link", name)
                link.setLink(tpl)
                link.Placement = P
                _PROBE.extend(_parts(probe))
                return link
            import ImportGui
            before = set(o.Name for o in _doc.Objects)
            ImportGui.insert(path, _doc.Name)
            new = [o for o in _doc.Objects if o.Name not in before]
            if new:
                part = _doc.addObject("App::Part", name)
                for o in [o for o in new if not any(p in new for p in o.InList)]:
                    part.addObject(o)
                part.Placement = P
                _MODEL_TEMPLATES[path] = part
                _PROBE.extend(_parts(probe))
                return part
        except Exception as e:
            App.Console.PrintWarning("HLayout: coloured import of %s failed (%s), "
                                     "reading plain shape\n" % (path, e))
    sh = base.copy()
    if mirrored:
        sh = sh.mirror(V(0, 0, 0), V(1, 0, 0))
    o = _doc.addObject("Part::Feature", name)
    o.Shape = sh
    o.Placement = P
    _PROBE.extend(_parts(o.Shape))
    return o


def _bondwire(p0, apex, p1, radius):
    """A swept loop p0 -> apex -> p1; falls back to a thin box path."""
    try:
        c = Part.BSplineCurve()
        c.interpolate([p0, apex, p1])
        spine = Part.Wire(c.toShape())
        prof = Part.Wire(Part.makeCircle(radius, p0, apex.sub(p0)))
        return spine.makePipeShell([prof], True, True)
    except Exception:
        legs = []
        for a, b in ((p0, apex), (apex, p1)):
            d = b.sub(a)
            L = d.Length
            if L > 1e-6:
                legs.append(Part.makeCylinder(radius, L, a, d))
        legs.append(Part.makeSphere(radius, apex))
        return _fuse(legs)


# --- layer 49 (L49) : z 0.0000..0.0100 mm ---
_s = []
_s.append(Part.Face([_poly([V(3.57600,1.83100,0.00000),V(3.42600,1.78500,0.00000),V(3.27000,1.77000,0.00000),V(3.11400,1.78500,0.00000),V(2.96400,1.83100,0.00000),V(2.82600,1.90500,0.00000),V(2.70400,2.00400,0.00000),V(2.60500,2.12600,0.00000),V(2.53100,2.26400,0.00000),V(2.48500,2.41400,0.00000),V(2.47000,2.57000,0.00000),V(2.48500,2.72600,0.00000),V(2.53100,2.87600,0.00000),V(2.60500,3.01400,0.00000),V(2.70400,3.13600,0.00000),V(2.82600,3.23500,0.00000),V(2.96400,3.30900,0.00000),V(3.11400,3.35500,0.00000),V(3.27000,3.37000,0.00000),V(3.42600,3.35500,0.00000),V(3.57600,3.30900,0.00000),V(3.71400,3.23500,0.00000),V(3.83600,3.13600,0.00000),V(3.93500,3.01400,0.00000),V(4.00900,2.87600,0.00000),V(4.05500,2.72600,0.00000),V(4.07000,2.57000,0.00000),V(4.05500,2.41400,0.00000),V(4.00900,2.26400,0.00000),V(3.93500,2.12600,0.00000),V(3.83600,2.00400,0.00000),V(3.71400,1.90500,0.00000),V(3.57600,1.83100,0.00000)])]).extrude(V(0,0,0.01000)))
_s.append(Part.Face([_poly([V(6.11600,1.83100,0.00000),V(5.96600,1.78500,0.00000),V(5.81000,1.77000,0.00000),V(5.65400,1.78500,0.00000),V(5.50400,1.83100,0.00000),V(5.36600,1.90500,0.00000),V(5.24400,2.00400,0.00000),V(5.14500,2.12600,0.00000),V(5.07100,2.26400,0.00000),V(5.02500,2.41400,0.00000),V(5.01000,2.57000,0.00000),V(5.02500,2.72600,0.00000),V(5.07100,2.87600,0.00000),V(5.14500,3.01400,0.00000),V(5.24400,3.13600,0.00000),V(5.36600,3.23500,0.00000),V(5.50400,3.30900,0.00000),V(5.65400,3.35500,0.00000),V(5.81000,3.37000,0.00000),V(5.96600,3.35500,0.00000),V(6.11600,3.30900,0.00000),V(6.25400,3.23500,0.00000),V(6.37600,3.13600,0.00000),V(6.47500,3.01400,0.00000),V(6.54900,2.87600,0.00000),V(6.59500,2.72600,0.00000),V(6.61000,2.57000,0.00000),V(6.59500,2.41400,0.00000),V(6.54900,2.26400,0.00000),V(6.47500,2.12600,0.00000),V(6.37600,2.00400,0.00000),V(6.25400,1.90500,0.00000),V(6.11600,1.83100,0.00000)])]).extrude(V(0,0,0.01000)))
_s.append(Part.Face([_poly([V(8.65600,1.83100,0.00000),V(8.50600,1.78500,0.00000),V(8.35000,1.77000,0.00000),V(8.19400,1.78500,0.00000),V(8.04400,1.83100,0.00000),V(7.90600,1.90500,0.00000),V(7.78400,2.00400,0.00000),V(7.68500,2.12600,0.00000),V(7.61100,2.26400,0.00000),V(7.56500,2.41400,0.00000),V(7.55000,2.57000,0.00000),V(7.56500,2.72600,0.00000),V(7.61100,2.87600,0.00000),V(7.68500,3.01400,0.00000),V(7.78400,3.13600,0.00000),V(7.90600,3.23500,0.00000),V(8.04400,3.30900,0.00000),V(8.19400,3.35500,0.00000),V(8.35000,3.37000,0.00000),V(8.50600,3.35500,0.00000),V(8.65600,3.30900,0.00000),V(8.79400,3.23500,0.00000),V(8.91600,3.13600,0.00000),V(9.01500,3.01400,0.00000),V(9.08900,2.87600,0.00000),V(9.13500,2.72600,0.00000),V(9.15000,2.57000,0.00000),V(9.13500,2.41400,0.00000),V(9.08900,2.26400,0.00000),V(9.01500,2.12600,0.00000),V(8.91600,2.00400,0.00000),V(8.79400,1.90500,0.00000),V(8.65600,1.83100,0.00000)])]).extrude(V(0,0,0.01000)))
_s.append(Part.Face([_poly([V(11.04600,1.78500,0.00000),V(10.89000,1.77000,0.00000),V(10.73400,1.78500,0.00000),V(10.58400,1.83100,0.00000),V(10.44600,1.90500,0.00000),V(10.32400,2.00400,0.00000),V(10.22500,2.12600,0.00000),V(10.15100,2.26400,0.00000),V(10.10500,2.41400,0.00000),V(10.09000,2.57000,0.00000),V(10.10500,2.72600,0.00000),V(10.15100,2.87600,0.00000),V(10.22500,3.01400,0.00000),V(10.32400,3.13600,0.00000),V(10.44600,3.23500,0.00000),V(10.58400,3.30900,0.00000),V(10.73400,3.35500,0.00000),V(10.89000,3.37000,0.00000),V(11.04600,3.35500,0.00000),V(11.19600,3.30900,0.00000),V(11.33400,3.23500,0.00000),V(11.45600,3.13600,0.00000),V(11.55500,3.01400,0.00000),V(11.62900,2.87600,0.00000),V(11.67500,2.72600,0.00000),V(11.69000,2.57000,0.00000),V(11.67500,2.41400,0.00000),V(11.62900,2.26400,0.00000),V(11.55500,2.12600,0.00000),V(11.45600,2.00400,0.00000),V(11.33400,1.90500,0.00000),V(11.19600,1.83100,0.00000),V(11.04600,1.78500,0.00000)])]).extrude(V(0,0,0.01000)))
_s.append(Part.Face([_poly([V(13.58600,1.78500,0.00000),V(13.43000,1.77000,0.00000),V(13.27400,1.78500,0.00000),V(13.12400,1.83100,0.00000),V(12.98600,1.90500,0.00000),V(12.86400,2.00400,0.00000),V(12.76500,2.12600,0.00000),V(12.69100,2.26400,0.00000),V(12.64500,2.41400,0.00000),V(12.63000,2.57000,0.00000),V(12.64500,2.72600,0.00000),V(12.69100,2.87600,0.00000),V(12.76500,3.01400,0.00000),V(12.86400,3.13600,0.00000),V(12.98600,3.23500,0.00000),V(13.12400,3.30900,0.00000),V(13.27400,3.35500,0.00000),V(13.43000,3.37000,0.00000),V(13.58600,3.35500,0.00000),V(13.73600,3.30900,0.00000),V(13.87400,3.23500,0.00000),V(13.99600,3.13600,0.00000),V(14.09500,3.01400,0.00000),V(14.16900,2.87600,0.00000),V(14.21500,2.72600,0.00000),V(14.23000,2.57000,0.00000),V(14.21500,2.41400,0.00000),V(14.16900,2.26400,0.00000),V(14.09500,2.12600,0.00000),V(13.99600,2.00400,0.00000),V(13.87400,1.90500,0.00000),V(13.73600,1.83100,0.00000),V(13.58600,1.78500,0.00000)])]).extrude(V(0,0,0.01000)))
_s.append(Part.Face([_poly([V(16.27600,1.83100,0.00000),V(16.12600,1.78500,0.00000),V(15.97000,1.77000,0.00000),V(15.81400,1.78500,0.00000),V(15.66400,1.83100,0.00000),V(15.52600,1.90500,0.00000),V(15.40400,2.00400,0.00000),V(15.30500,2.12600,0.00000),V(15.23100,2.26400,0.00000),V(15.18500,2.41400,0.00000),V(15.17000,2.57000,0.00000),V(15.18500,2.72600,0.00000),V(15.23100,2.87600,0.00000),V(15.30500,3.01400,0.00000),V(15.40400,3.13600,0.00000),V(15.52600,3.23500,0.00000),V(15.66400,3.30900,0.00000),V(15.81400,3.35500,0.00000),V(15.97000,3.37000,0.00000),V(16.12600,3.35500,0.00000),V(16.27600,3.30900,0.00000),V(16.41400,3.23500,0.00000),V(16.53600,3.13600,0.00000),V(16.63500,3.01400,0.00000),V(16.70900,2.87600,0.00000),V(16.75500,2.72600,0.00000),V(16.77000,2.57000,0.00000),V(16.75500,2.41400,0.00000),V(16.70900,2.26400,0.00000),V(16.63500,2.12600,0.00000),V(16.53600,2.00400,0.00000),V(16.41400,1.90500,0.00000),V(16.27600,1.83100,0.00000)])]).extrude(V(0,0,0.01000)))
_s.append(Part.Face([_poly([V(18.66600,1.78500,0.00000),V(18.51000,1.77000,0.00000),V(18.35400,1.78500,0.00000),V(18.20400,1.83100,0.00000),V(18.06600,1.90500,0.00000),V(17.94400,2.00400,0.00000),V(17.84500,2.12600,0.00000),V(17.77100,2.26400,0.00000),V(17.72500,2.41400,0.00000),V(17.71000,2.57000,0.00000),V(17.72500,2.72600,0.00000),V(17.77100,2.87600,0.00000),V(17.84500,3.01400,0.00000),V(17.94400,3.13600,0.00000),V(18.06600,3.23500,0.00000),V(18.20400,3.30900,0.00000),V(18.35400,3.35500,0.00000),V(18.51000,3.37000,0.00000),V(18.66600,3.35500,0.00000),V(18.81600,3.30900,0.00000),V(18.95400,3.23500,0.00000),V(19.07600,3.13600,0.00000),V(19.17500,3.01400,0.00000),V(19.24900,2.87600,0.00000),V(19.29500,2.72600,0.00000),V(19.31000,2.57000,0.00000),V(19.29500,2.41400,0.00000),V(19.24900,2.26400,0.00000),V(19.17500,2.12600,0.00000),V(19.07600,2.00400,0.00000),V(18.95400,1.90500,0.00000),V(18.81600,1.83100,0.00000),V(18.66600,1.78500,0.00000)])]).extrude(V(0,0,0.01000)))
_s.append(Part.Face([_poly([V(21.20600,1.78500,0.00000),V(21.05000,1.77000,0.00000),V(20.89400,1.78500,0.00000),V(20.74400,1.83100,0.00000),V(20.60600,1.90500,0.00000),V(20.48400,2.00400,0.00000),V(20.38500,2.12600,0.00000),V(20.31100,2.26400,0.00000),V(20.26500,2.41400,0.00000),V(20.25000,2.57000,0.00000),V(20.26500,2.72600,0.00000),V(20.31100,2.87600,0.00000),V(20.38500,3.01400,0.00000),V(20.48400,3.13600,0.00000),V(20.60600,3.23500,0.00000),V(20.74400,3.30900,0.00000),V(20.89400,3.35500,0.00000),V(21.05000,3.37000,0.00000),V(21.20600,3.35500,0.00000),V(21.35600,3.30900,0.00000),V(21.49400,3.23500,0.00000),V(21.61600,3.13600,0.00000),V(21.71500,3.01400,0.00000),V(21.78900,2.87600,0.00000),V(21.83500,2.72600,0.00000),V(21.85000,2.57000,0.00000),V(21.83500,2.41400,0.00000),V(21.78900,2.26400,0.00000),V(21.71500,2.12600,0.00000),V(21.61600,2.00400,0.00000),V(21.49400,1.90500,0.00000),V(21.35600,1.83100,0.00000),V(21.20600,1.78500,0.00000)])]).extrude(V(0,0,0.01000)))
_s.append(Part.Face([_poly([V(23.89600,1.83100,0.00000),V(23.74600,1.78500,0.00000),V(23.59000,1.77000,0.00000),V(23.43400,1.78500,0.00000),V(23.28400,1.83100,0.00000),V(23.14600,1.90500,0.00000),V(23.02400,2.00400,0.00000),V(22.92500,2.12600,0.00000),V(22.85100,2.26400,0.00000),V(22.80500,2.41400,0.00000),V(22.79000,2.57000,0.00000),V(22.80500,2.72600,0.00000),V(22.85100,2.87600,0.00000),V(22.92500,3.01400,0.00000),V(23.02400,3.13600,0.00000),V(23.14600,3.23500,0.00000),V(23.28400,3.30900,0.00000),V(23.43400,3.35500,0.00000),V(23.59000,3.37000,0.00000),V(23.74600,3.35500,0.00000),V(23.89600,3.30900,0.00000),V(24.03400,3.23500,0.00000),V(24.15600,3.13600,0.00000),V(24.25500,3.01400,0.00000),V(24.32900,2.87600,0.00000),V(24.37500,2.72600,0.00000),V(24.39000,2.57000,0.00000),V(24.37500,2.41400,0.00000),V(24.32900,2.26400,0.00000),V(24.25500,2.12600,0.00000),V(24.15600,2.00400,0.00000),V(24.03400,1.90500,0.00000),V(23.89600,1.83100,0.00000)])]).extrude(V(0,0,0.01000)))
_s.append(Part.Face([_poly([V(26.28600,1.78500,0.00000),V(26.13000,1.77000,0.00000),V(25.97400,1.78500,0.00000),V(25.82400,1.83100,0.00000),V(25.68600,1.90500,0.00000),V(25.56400,2.00400,0.00000),V(25.46500,2.12600,0.00000),V(25.39100,2.26400,0.00000),V(25.34500,2.41400,0.00000),V(25.33000,2.57000,0.00000),V(25.34500,2.72600,0.00000),V(25.39100,2.87600,0.00000),V(25.46500,3.01400,0.00000),V(25.56400,3.13600,0.00000),V(25.68600,3.23500,0.00000),V(25.82400,3.30900,0.00000),V(25.97400,3.35500,0.00000),V(26.13000,3.37000,0.00000),V(26.28600,3.35500,0.00000),V(26.43600,3.30900,0.00000),V(26.57400,3.23500,0.00000),V(26.69600,3.13600,0.00000),V(26.79500,3.01400,0.00000),V(26.86900,2.87600,0.00000),V(26.91500,2.72600,0.00000),V(26.93000,2.57000,0.00000),V(26.91500,2.41400,0.00000),V(26.86900,2.26400,0.00000),V(26.79500,2.12600,0.00000),V(26.69600,2.00400,0.00000),V(26.57400,1.90500,0.00000),V(26.43600,1.83100,0.00000),V(26.28600,1.78500,0.00000)])]).extrude(V(0,0,0.01000)))
_s.append(Part.Face([_poly([V(40.82600,1.78500,0.00000),V(40.67000,1.77000,0.00000),V(40.51400,1.78500,0.00000),V(40.36400,1.83100,0.00000),V(40.22600,1.90500,0.00000),V(40.10400,2.00400,0.00000),V(40.00500,2.12600,0.00000),V(39.93100,2.26400,0.00000),V(39.88500,2.41400,0.00000),V(39.87000,2.57000,0.00000),V(39.88500,2.72600,0.00000),V(39.93100,2.87600,0.00000),V(40.00500,3.01400,0.00000),V(40.10400,3.13600,0.00000),V(40.22600,3.23500,0.00000),V(40.36400,3.30900,0.00000),V(40.51400,3.35500,0.00000),V(40.67000,3.37000,0.00000),V(40.82600,3.35500,0.00000),V(40.97600,3.30900,0.00000),V(41.11400,3.23500,0.00000),V(41.23600,3.13600,0.00000),V(41.33500,3.01400,0.00000),V(41.40900,2.87600,0.00000),V(41.45500,2.72600,0.00000),V(41.47000,2.57000,0.00000),V(41.45500,2.41400,0.00000),V(41.40900,2.26400,0.00000),V(41.33500,2.12600,0.00000),V(41.23600,2.00400,0.00000),V(41.11400,1.90500,0.00000),V(40.97600,1.83100,0.00000),V(40.82600,1.78500,0.00000)])]).extrude(V(0,0,0.01000)))
_s.append(Part.Face([_poly([V(43.51600,1.83100,0.00000),V(43.36600,1.78500,0.00000),V(43.21000,1.77000,0.00000),V(43.05400,1.78500,0.00000),V(42.90400,1.83100,0.00000),V(42.76600,1.90500,0.00000),V(42.64400,2.00400,0.00000),V(42.54500,2.12600,0.00000),V(42.47100,2.26400,0.00000),V(42.42500,2.41400,0.00000),V(42.41000,2.57000,0.00000),V(42.42500,2.72600,0.00000),V(42.47100,2.87600,0.00000),V(42.54500,3.01400,0.00000),V(42.64400,3.13600,0.00000),V(42.76600,3.23500,0.00000),V(42.90400,3.30900,0.00000),V(43.05400,3.35500,0.00000),V(43.21000,3.37000,0.00000),V(43.36600,3.35500,0.00000),V(43.51600,3.30900,0.00000),V(43.65400,3.23500,0.00000),V(43.77600,3.13600,0.00000),V(43.87500,3.01400,0.00000),V(43.94900,2.87600,0.00000),V(43.99500,2.72600,0.00000),V(44.01000,2.57000,0.00000),V(43.99500,2.41400,0.00000),V(43.94900,2.26400,0.00000),V(43.87500,2.12600,0.00000),V(43.77600,2.00400,0.00000),V(43.65400,1.90500,0.00000),V(43.51600,1.83100,0.00000)])]).extrude(V(0,0,0.01000)))
_s.append(Part.Face([_poly([V(46.05600,1.83100,0.00000),V(45.90600,1.78500,0.00000),V(45.75000,1.77000,0.00000),V(45.59400,1.78500,0.00000),V(45.44400,1.83100,0.00000),V(45.30600,1.90500,0.00000),V(45.18400,2.00400,0.00000),V(45.08500,2.12600,0.00000),V(45.01100,2.26400,0.00000),V(44.96500,2.41400,0.00000),V(44.95000,2.57000,0.00000),V(44.96500,2.72600,0.00000),V(45.01100,2.87600,0.00000),V(45.08500,3.01400,0.00000),V(45.18400,3.13600,0.00000),V(45.30600,3.23500,0.00000),V(45.44400,3.30900,0.00000),V(45.59400,3.35500,0.00000),V(45.75000,3.37000,0.00000),V(45.90600,3.35500,0.00000),V(46.05600,3.30900,0.00000),V(46.19400,3.23500,0.00000),V(46.31600,3.13600,0.00000),V(46.41500,3.01400,0.00000),V(46.48900,2.87600,0.00000),V(46.53500,2.72600,0.00000),V(46.55000,2.57000,0.00000),V(46.53500,2.41400,0.00000),V(46.48900,2.26400,0.00000),V(46.41500,2.12600,0.00000),V(46.31600,2.00400,0.00000),V(46.19400,1.90500,0.00000),V(46.05600,1.83100,0.00000)])]).extrude(V(0,0,0.01000)))
_s.append(Part.Face([_poly([V(48.59600,1.83100,0.00000),V(48.44600,1.78500,0.00000),V(48.29000,1.77000,0.00000),V(48.13400,1.78500,0.00000),V(47.98400,1.83100,0.00000),V(47.84600,1.90500,0.00000),V(47.72400,2.00400,0.00000),V(47.62500,2.12600,0.00000),V(47.55100,2.26400,0.00000),V(47.50500,2.41400,0.00000),V(47.49000,2.57000,0.00000),V(47.50500,2.72600,0.00000),V(47.55100,2.87600,0.00000),V(47.62500,3.01400,0.00000),V(47.72400,3.13600,0.00000),V(47.84600,3.23500,0.00000),V(47.98400,3.30900,0.00000),V(48.13400,3.35500,0.00000),V(48.29000,3.37000,0.00000),V(48.44600,3.35500,0.00000),V(48.59600,3.30900,0.00000),V(48.73400,3.23500,0.00000),V(48.85600,3.13600,0.00000),V(48.95500,3.01400,0.00000),V(49.02900,2.87600,0.00000),V(49.07500,2.72600,0.00000),V(49.09000,2.57000,0.00000),V(49.07500,2.41400,0.00000),V(49.02900,2.26400,0.00000),V(48.95500,2.12600,0.00000),V(48.85600,2.00400,0.00000),V(48.73400,1.90500,0.00000),V(48.59600,1.83100,0.00000)])]).extrude(V(0,0,0.01000)))
_s.append(Part.Face([_poly([V(50.98600,1.78500,0.00000),V(50.83000,1.77000,0.00000),V(50.67400,1.78500,0.00000),V(50.52400,1.83100,0.00000),V(50.38600,1.90500,0.00000),V(50.26400,2.00400,0.00000),V(50.16500,2.12600,0.00000),V(50.09100,2.26400,0.00000),V(50.04500,2.41400,0.00000),V(50.03000,2.57000,0.00000),V(50.04500,2.72600,0.00000),V(50.09100,2.87600,0.00000),V(50.16500,3.01400,0.00000),V(50.26400,3.13600,0.00000),V(50.38600,3.23500,0.00000),V(50.52400,3.30900,0.00000),V(50.67400,3.35500,0.00000),V(50.83000,3.37000,0.00000),V(50.98600,3.35500,0.00000),V(51.13600,3.30900,0.00000),V(51.27400,3.23500,0.00000),V(51.39600,3.13600,0.00000),V(51.49500,3.01400,0.00000),V(51.56900,2.87600,0.00000),V(51.61500,2.72600,0.00000),V(51.63000,2.57000,0.00000),V(51.61500,2.41400,0.00000),V(51.56900,2.26400,0.00000),V(51.49500,2.12600,0.00000),V(51.39600,2.00400,0.00000),V(51.27400,1.90500,0.00000),V(51.13600,1.83100,0.00000),V(50.98600,1.78500,0.00000)])]).extrude(V(0,0,0.01000)))
_s.append(Part.Face([_poly([V(3.42600,24.64500,0.00000),V(3.27000,24.63000,0.00000),V(3.11400,24.64500,0.00000),V(2.96400,24.69100,0.00000),V(2.82600,24.76500,0.00000),V(2.70400,24.86400,0.00000),V(2.60500,24.98600,0.00000),V(2.53100,25.12400,0.00000),V(2.48500,25.27400,0.00000),V(2.47000,25.43000,0.00000),V(2.48500,25.58600,0.00000),V(2.53100,25.73600,0.00000),V(2.60500,25.87400,0.00000),V(2.70400,25.99600,0.00000),V(2.82600,26.09500,0.00000),V(2.96400,26.16900,0.00000),V(3.11400,26.21500,0.00000),V(3.27000,26.23000,0.00000),V(3.42600,26.21500,0.00000),V(3.57600,26.16900,0.00000),V(3.71400,26.09500,0.00000),V(3.83600,25.99600,0.00000),V(3.93500,25.87400,0.00000),V(4.00900,25.73600,0.00000),V(4.05500,25.58600,0.00000),V(4.07000,25.43000,0.00000),V(4.05500,25.27400,0.00000),V(4.00900,25.12400,0.00000),V(3.93500,24.98600,0.00000),V(3.83600,24.86400,0.00000),V(3.71400,24.76500,0.00000),V(3.57600,24.69100,0.00000),V(3.42600,24.64500,0.00000)])]).extrude(V(0,0,0.01000)))
_s.append(Part.Face([_poly([V(6.11600,24.69100,0.00000),V(5.96600,24.64500,0.00000),V(5.81000,24.63000,0.00000),V(5.65400,24.64500,0.00000),V(5.50400,24.69100,0.00000),V(5.36600,24.76500,0.00000),V(5.24400,24.86400,0.00000),V(5.14500,24.98600,0.00000),V(5.07100,25.12400,0.00000),V(5.02500,25.27400,0.00000),V(5.01000,25.43000,0.00000),V(5.02500,25.58600,0.00000),V(5.07100,25.73600,0.00000),V(5.14500,25.87400,0.00000),V(5.24400,25.99600,0.00000),V(5.36600,26.09500,0.00000),V(5.50400,26.16900,0.00000),V(5.65400,26.21500,0.00000),V(5.81000,26.23000,0.00000),V(5.96600,26.21500,0.00000),V(6.11600,26.16900,0.00000),V(6.25400,26.09500,0.00000),V(6.37600,25.99600,0.00000),V(6.47500,25.87400,0.00000),V(6.54900,25.73600,0.00000),V(6.59500,25.58600,0.00000),V(6.61000,25.43000,0.00000),V(6.59500,25.27400,0.00000),V(6.54900,25.12400,0.00000),V(6.47500,24.98600,0.00000),V(6.37600,24.86400,0.00000),V(6.25400,24.76500,0.00000),V(6.11600,24.69100,0.00000)])]).extrude(V(0,0,0.01000)))
_s.append(Part.Face([_poly([V(8.50600,24.64500,0.00000),V(8.35000,24.63000,0.00000),V(8.19400,24.64500,0.00000),V(8.04400,24.69100,0.00000),V(7.90600,24.76500,0.00000),V(7.78400,24.86400,0.00000),V(7.68500,24.98600,0.00000),V(7.61100,25.12400,0.00000),V(7.56500,25.27400,0.00000),V(7.55000,25.43000,0.00000),V(7.56500,25.58600,0.00000),V(7.61100,25.73600,0.00000),V(7.68500,25.87400,0.00000),V(7.78400,25.99600,0.00000),V(7.90600,26.09500,0.00000),V(8.04400,26.16900,0.00000),V(8.19400,26.21500,0.00000),V(8.35000,26.23000,0.00000),V(8.50600,26.21500,0.00000),V(8.65600,26.16900,0.00000),V(8.79400,26.09500,0.00000),V(8.91600,25.99600,0.00000),V(9.01500,25.87400,0.00000),V(9.08900,25.73600,0.00000),V(9.13500,25.58600,0.00000),V(9.15000,25.43000,0.00000),V(9.13500,25.27400,0.00000),V(9.08900,25.12400,0.00000),V(9.01500,24.98600,0.00000),V(8.91600,24.86400,0.00000),V(8.79400,24.76500,0.00000),V(8.65600,24.69100,0.00000),V(8.50600,24.64500,0.00000)])]).extrude(V(0,0,0.01000)))
_s.append(Part.Face([_poly([V(11.04600,24.64500,0.00000),V(10.89000,24.63000,0.00000),V(10.73400,24.64500,0.00000),V(10.58400,24.69100,0.00000),V(10.44600,24.76500,0.00000),V(10.32400,24.86400,0.00000),V(10.22500,24.98600,0.00000),V(10.15100,25.12400,0.00000),V(10.10500,25.27400,0.00000),V(10.09000,25.43000,0.00000),V(10.10500,25.58600,0.00000),V(10.15100,25.73600,0.00000),V(10.22500,25.87400,0.00000),V(10.32400,25.99600,0.00000),V(10.44600,26.09500,0.00000),V(10.58400,26.16900,0.00000),V(10.73400,26.21500,0.00000),V(10.89000,26.23000,0.00000),V(11.04600,26.21500,0.00000),V(11.19600,26.16900,0.00000),V(11.33400,26.09500,0.00000),V(11.45600,25.99600,0.00000),V(11.55500,25.87400,0.00000),V(11.62900,25.73600,0.00000),V(11.67500,25.58600,0.00000),V(11.69000,25.43000,0.00000),V(11.67500,25.27400,0.00000),V(11.62900,25.12400,0.00000),V(11.55500,24.98600,0.00000),V(11.45600,24.86400,0.00000),V(11.33400,24.76500,0.00000),V(11.19600,24.69100,0.00000),V(11.04600,24.64500,0.00000)])]).extrude(V(0,0,0.01000)))
_s.append(Part.Face([_poly([V(13.73600,24.69100,0.00000),V(13.58600,24.64500,0.00000),V(13.43000,24.63000,0.00000),V(13.27400,24.64500,0.00000),V(13.12400,24.69100,0.00000),V(12.98600,24.76500,0.00000),V(12.86400,24.86400,0.00000),V(12.76500,24.98600,0.00000),V(12.69100,25.12400,0.00000),V(12.64500,25.27400,0.00000),V(12.63000,25.43000,0.00000),V(12.64500,25.58600,0.00000),V(12.69100,25.73600,0.00000),V(12.76500,25.87400,0.00000),V(12.86400,25.99600,0.00000),V(12.98600,26.09500,0.00000),V(13.12400,26.16900,0.00000),V(13.27400,26.21500,0.00000),V(13.43000,26.23000,0.00000),V(13.58600,26.21500,0.00000),V(13.73600,26.16900,0.00000),V(13.87400,26.09500,0.00000),V(13.99600,25.99600,0.00000),V(14.09500,25.87400,0.00000),V(14.16900,25.73600,0.00000),V(14.21500,25.58600,0.00000),V(14.23000,25.43000,0.00000),V(14.21500,25.27400,0.00000),V(14.16900,25.12400,0.00000),V(14.09500,24.98600,0.00000),V(13.99600,24.86400,0.00000),V(13.87400,24.76500,0.00000),V(13.73600,24.69100,0.00000)])]).extrude(V(0,0,0.01000)))
_s.append(Part.Face([_poly([V(16.12600,24.64500,0.00000),V(15.97000,24.63000,0.00000),V(15.81400,24.64500,0.00000),V(15.66400,24.69100,0.00000),V(15.52600,24.76500,0.00000),V(15.40400,24.86400,0.00000),V(15.30500,24.98600,0.00000),V(15.23100,25.12400,0.00000),V(15.18500,25.27400,0.00000),V(15.17000,25.43000,0.00000),V(15.18500,25.58600,0.00000),V(15.23100,25.73600,0.00000),V(15.30500,25.87400,0.00000),V(15.40400,25.99600,0.00000),V(15.52600,26.09500,0.00000),V(15.66400,26.16900,0.00000),V(15.81400,26.21500,0.00000),V(15.97000,26.23000,0.00000),V(16.12600,26.21500,0.00000),V(16.27600,26.16900,0.00000),V(16.41400,26.09500,0.00000),V(16.53600,25.99600,0.00000),V(16.63500,25.87400,0.00000),V(16.70900,25.73600,0.00000),V(16.75500,25.58600,0.00000),V(16.77000,25.43000,0.00000),V(16.75500,25.27400,0.00000),V(16.70900,25.12400,0.00000),V(16.63500,24.98600,0.00000),V(16.53600,24.86400,0.00000),V(16.41400,24.76500,0.00000),V(16.27600,24.69100,0.00000),V(16.12600,24.64500,0.00000)])]).extrude(V(0,0,0.01000)))
_s.append(Part.Face([_poly([V(18.66600,24.64500,0.00000),V(18.51000,24.63000,0.00000),V(18.35400,24.64500,0.00000),V(18.20400,24.69100,0.00000),V(18.06600,24.76500,0.00000),V(17.94400,24.86400,0.00000),V(17.84500,24.98600,0.00000),V(17.77100,25.12400,0.00000),V(17.72500,25.27400,0.00000),V(17.71000,25.43000,0.00000),V(17.72500,25.58600,0.00000),V(17.77100,25.73600,0.00000),V(17.84500,25.87400,0.00000),V(17.94400,25.99600,0.00000),V(18.06600,26.09500,0.00000),V(18.20400,26.16900,0.00000),V(18.35400,26.21500,0.00000),V(18.51000,26.23000,0.00000),V(18.66600,26.21500,0.00000),V(18.81600,26.16900,0.00000),V(18.95400,26.09500,0.00000),V(19.07600,25.99600,0.00000),V(19.17500,25.87400,0.00000),V(19.24900,25.73600,0.00000),V(19.29500,25.58600,0.00000),V(19.31000,25.43000,0.00000),V(19.29500,25.27400,0.00000),V(19.24900,25.12400,0.00000),V(19.17500,24.98600,0.00000),V(19.07600,24.86400,0.00000),V(18.95400,24.76500,0.00000),V(18.81600,24.69100,0.00000),V(18.66600,24.64500,0.00000)])]).extrude(V(0,0,0.01000)))
_s.append(Part.Face([_poly([V(21.35600,24.69100,0.00000),V(21.20600,24.64500,0.00000),V(21.05000,24.63000,0.00000),V(20.89400,24.64500,0.00000),V(20.74400,24.69100,0.00000),V(20.60600,24.76500,0.00000),V(20.48400,24.86400,0.00000),V(20.38500,24.98600,0.00000),V(20.31100,25.12400,0.00000),V(20.26500,25.27400,0.00000),V(20.25000,25.43000,0.00000),V(20.26500,25.58600,0.00000),V(20.31100,25.73600,0.00000),V(20.38500,25.87400,0.00000),V(20.48400,25.99600,0.00000),V(20.60600,26.09500,0.00000),V(20.74400,26.16900,0.00000),V(20.89400,26.21500,0.00000),V(21.05000,26.23000,0.00000),V(21.20600,26.21500,0.00000),V(21.35600,26.16900,0.00000),V(21.49400,26.09500,0.00000),V(21.61600,25.99600,0.00000),V(21.71500,25.87400,0.00000),V(21.78900,25.73600,0.00000),V(21.83500,25.58600,0.00000),V(21.85000,25.43000,0.00000),V(21.83500,25.27400,0.00000),V(21.78900,25.12400,0.00000),V(21.71500,24.98600,0.00000),V(21.61600,24.86400,0.00000),V(21.49400,24.76500,0.00000),V(21.35600,24.69100,0.00000)])]).extrude(V(0,0,0.01000)))
_s.append(Part.Face([_poly([V(23.89600,24.69100,0.00000),V(23.74600,24.64500,0.00000),V(23.59000,24.63000,0.00000),V(23.43400,24.64500,0.00000),V(23.28400,24.69100,0.00000),V(23.14600,24.76500,0.00000),V(23.02400,24.86400,0.00000),V(22.92500,24.98600,0.00000),V(22.85100,25.12400,0.00000),V(22.80500,25.27400,0.00000),V(22.79000,25.43000,0.00000),V(22.80500,25.58600,0.00000),V(22.85100,25.73600,0.00000),V(22.92500,25.87400,0.00000),V(23.02400,25.99600,0.00000),V(23.14600,26.09500,0.00000),V(23.28400,26.16900,0.00000),V(23.43400,26.21500,0.00000),V(23.59000,26.23000,0.00000),V(23.74600,26.21500,0.00000),V(23.89600,26.16900,0.00000),V(24.03400,26.09500,0.00000),V(24.15600,25.99600,0.00000),V(24.25500,25.87400,0.00000),V(24.32900,25.73600,0.00000),V(24.37500,25.58600,0.00000),V(24.39000,25.43000,0.00000),V(24.37500,25.27400,0.00000),V(24.32900,25.12400,0.00000),V(24.25500,24.98600,0.00000),V(24.15600,24.86400,0.00000),V(24.03400,24.76500,0.00000),V(23.89600,24.69100,0.00000)])]).extrude(V(0,0,0.01000)))
_s.append(Part.Face([_poly([V(26.43600,24.69100,0.00000),V(26.28600,24.64500,0.00000),V(26.13000,24.63000,0.00000),V(25.97400,24.64500,0.00000),V(25.82400,24.69100,0.00000),V(25.68600,24.76500,0.00000),V(25.56400,24.86400,0.00000),V(25.46500,24.98600,0.00000),V(25.39100,25.12400,0.00000),V(25.34500,25.27400,0.00000),V(25.33000,25.43000,0.00000),V(25.34500,25.58600,0.00000),V(25.39100,25.73600,0.00000),V(25.46500,25.87400,0.00000),V(25.56400,25.99600,0.00000),V(25.68600,26.09500,0.00000),V(25.82400,26.16900,0.00000),V(25.97400,26.21500,0.00000),V(26.13000,26.23000,0.00000),V(26.28600,26.21500,0.00000),V(26.43600,26.16900,0.00000),V(26.57400,26.09500,0.00000),V(26.69600,25.99600,0.00000),V(26.79500,25.87400,0.00000),V(26.86900,25.73600,0.00000),V(26.91500,25.58600,0.00000),V(26.93000,25.43000,0.00000),V(26.91500,25.27400,0.00000),V(26.86900,25.12400,0.00000),V(26.79500,24.98600,0.00000),V(26.69600,24.86400,0.00000),V(26.57400,24.76500,0.00000),V(26.43600,24.69100,0.00000)])]).extrude(V(0,0,0.01000)))
_s.append(Part.Face([_poly([V(40.82600,24.64500,0.00000),V(40.67000,24.63000,0.00000),V(40.51400,24.64500,0.00000),V(40.36400,24.69100,0.00000),V(40.22600,24.76500,0.00000),V(40.10400,24.86400,0.00000),V(40.00500,24.98600,0.00000),V(39.93100,25.12400,0.00000),V(39.88500,25.27400,0.00000),V(39.87000,25.43000,0.00000),V(39.88500,25.58600,0.00000),V(39.93100,25.73600,0.00000),V(40.00500,25.87400,0.00000),V(40.10400,25.99600,0.00000),V(40.22600,26.09500,0.00000),V(40.36400,26.16900,0.00000),V(40.51400,26.21500,0.00000),V(40.67000,26.23000,0.00000),V(40.82600,26.21500,0.00000),V(40.97600,26.16900,0.00000),V(41.11400,26.09500,0.00000),V(41.23600,25.99600,0.00000),V(41.33500,25.87400,0.00000),V(41.40900,25.73600,0.00000),V(41.45500,25.58600,0.00000),V(41.47000,25.43000,0.00000),V(41.45500,25.27400,0.00000),V(41.40900,25.12400,0.00000),V(41.33500,24.98600,0.00000),V(41.23600,24.86400,0.00000),V(41.11400,24.76500,0.00000),V(40.97600,24.69100,0.00000),V(40.82600,24.64500,0.00000)])]).extrude(V(0,0,0.01000)))
_s.append(Part.Face([_poly([V(43.36600,24.64500,0.00000),V(43.21000,24.63000,0.00000),V(43.05400,24.64500,0.00000),V(42.90400,24.69100,0.00000),V(42.76600,24.76500,0.00000),V(42.64400,24.86400,0.00000),V(42.54500,24.98600,0.00000),V(42.47100,25.12400,0.00000),V(42.42500,25.27400,0.00000),V(42.41000,25.43000,0.00000),V(42.42500,25.58600,0.00000),V(42.47100,25.73600,0.00000),V(42.54500,25.87400,0.00000),V(42.64400,25.99600,0.00000),V(42.76600,26.09500,0.00000),V(42.90400,26.16900,0.00000),V(43.05400,26.21500,0.00000),V(43.21000,26.23000,0.00000),V(43.36600,26.21500,0.00000),V(43.51600,26.16900,0.00000),V(43.65400,26.09500,0.00000),V(43.77600,25.99600,0.00000),V(43.87500,25.87400,0.00000),V(43.94900,25.73600,0.00000),V(43.99500,25.58600,0.00000),V(44.01000,25.43000,0.00000),V(43.99500,25.27400,0.00000),V(43.94900,25.12400,0.00000),V(43.87500,24.98600,0.00000),V(43.77600,24.86400,0.00000),V(43.65400,24.76500,0.00000),V(43.51600,24.69100,0.00000),V(43.36600,24.64500,0.00000)])]).extrude(V(0,0,0.01000)))
_s.append(Part.Face([_poly([V(46.05600,24.69100,0.00000),V(45.90600,24.64500,0.00000),V(45.75000,24.63000,0.00000),V(45.59400,24.64500,0.00000),V(45.44400,24.69100,0.00000),V(45.30600,24.76500,0.00000),V(45.18400,24.86400,0.00000),V(45.08500,24.98600,0.00000),V(45.01100,25.12400,0.00000),V(44.96500,25.27400,0.00000),V(44.95000,25.43000,0.00000),V(44.96500,25.58600,0.00000),V(45.01100,25.73600,0.00000),V(45.08500,25.87400,0.00000),V(45.18400,25.99600,0.00000),V(45.30600,26.09500,0.00000),V(45.44400,26.16900,0.00000),V(45.59400,26.21500,0.00000),V(45.75000,26.23000,0.00000),V(45.90600,26.21500,0.00000),V(46.05600,26.16900,0.00000),V(46.19400,26.09500,0.00000),V(46.31600,25.99600,0.00000),V(46.41500,25.87400,0.00000),V(46.48900,25.73600,0.00000),V(46.53500,25.58600,0.00000),V(46.55000,25.43000,0.00000),V(46.53500,25.27400,0.00000),V(46.48900,25.12400,0.00000),V(46.41500,24.98600,0.00000),V(46.31600,24.86400,0.00000),V(46.19400,24.76500,0.00000),V(46.05600,24.69100,0.00000)])]).extrude(V(0,0,0.01000)))
_s.append(Part.Face([_poly([V(48.44600,24.64500,0.00000),V(48.29000,24.63000,0.00000),V(48.13400,24.64500,0.00000),V(47.98400,24.69100,0.00000),V(47.84600,24.76500,0.00000),V(47.72400,24.86400,0.00000),V(47.62500,24.98600,0.00000),V(47.55100,25.12400,0.00000),V(47.50500,25.27400,0.00000),V(47.49000,25.43000,0.00000),V(47.50500,25.58600,0.00000),V(47.55100,25.73600,0.00000),V(47.62500,25.87400,0.00000),V(47.72400,25.99600,0.00000),V(47.84600,26.09500,0.00000),V(47.98400,26.16900,0.00000),V(48.13400,26.21500,0.00000),V(48.29000,26.23000,0.00000),V(48.44600,26.21500,0.00000),V(48.59600,26.16900,0.00000),V(48.73400,26.09500,0.00000),V(48.85600,25.99600,0.00000),V(48.95500,25.87400,0.00000),V(49.02900,25.73600,0.00000),V(49.07500,25.58600,0.00000),V(49.09000,25.43000,0.00000),V(49.07500,25.27400,0.00000),V(49.02900,25.12400,0.00000),V(48.95500,24.98600,0.00000),V(48.85600,24.86400,0.00000),V(48.73400,24.76500,0.00000),V(48.59600,24.69100,0.00000),V(48.44600,24.64500,0.00000)])]).extrude(V(0,0,0.01000)))
_s.append(Part.Face([_poly([V(50.98600,24.64500,0.00000),V(50.83000,24.63000,0.00000),V(50.67400,24.64500,0.00000),V(50.52400,24.69100,0.00000),V(50.38600,24.76500,0.00000),V(50.26400,24.86400,0.00000),V(50.16500,24.98600,0.00000),V(50.09100,25.12400,0.00000),V(50.04500,25.27400,0.00000),V(50.03000,25.43000,0.00000),V(50.04500,25.58600,0.00000),V(50.09100,25.73600,0.00000),V(50.16500,25.87400,0.00000),V(50.26400,25.99600,0.00000),V(50.38600,26.09500,0.00000),V(50.52400,26.16900,0.00000),V(50.67400,26.21500,0.00000),V(50.83000,26.23000,0.00000),V(50.98600,26.21500,0.00000),V(51.13600,26.16900,0.00000),V(51.27400,26.09500,0.00000),V(51.39600,25.99600,0.00000),V(51.49500,25.87400,0.00000),V(51.56900,25.73600,0.00000),V(51.61500,25.58600,0.00000),V(51.63000,25.43000,0.00000),V(51.61500,25.27400,0.00000),V(51.56900,25.12400,0.00000),V(51.49500,24.98600,0.00000),V(51.39600,24.86400,0.00000),V(51.27400,24.76500,0.00000),V(51.13600,24.69100,0.00000),V(50.98600,24.64500,0.00000)])]).extrude(V(0,0,0.01000)))
_s.append(Part.Face([_poly([V(53.67600,1.83100,0.00000),V(53.52600,1.78500,0.00000),V(53.37000,1.77000,0.00000),V(53.21400,1.78500,0.00000),V(53.06400,1.83100,0.00000),V(52.92600,1.90500,0.00000),V(52.80400,2.00400,0.00000),V(52.70500,2.12600,0.00000),V(52.63100,2.26400,0.00000),V(52.58500,2.41400,0.00000),V(52.57000,2.57000,0.00000),V(52.58500,2.72600,0.00000),V(52.63100,2.87600,0.00000),V(52.70500,3.01400,0.00000),V(52.80400,3.13600,0.00000),V(52.92600,3.23500,0.00000),V(53.06400,3.30900,0.00000),V(53.21400,3.35500,0.00000),V(53.37000,3.37000,0.00000),V(53.52600,3.35500,0.00000),V(53.67600,3.30900,0.00000),V(53.81400,3.23500,0.00000),V(53.93600,3.13600,0.00000),V(54.03500,3.01400,0.00000),V(54.10900,2.87600,0.00000),V(54.15500,2.72600,0.00000),V(54.17000,2.57000,0.00000),V(54.15500,2.41400,0.00000),V(54.10900,2.26400,0.00000),V(54.03500,2.12600,0.00000),V(53.93600,2.00400,0.00000),V(53.81400,1.90500,0.00000),V(53.67600,1.83100,0.00000)])]).extrude(V(0,0,0.01000)))
_s.append(Part.Face([_poly([V(56.06600,1.78500,0.00000),V(55.91000,1.77000,0.00000),V(55.75400,1.78500,0.00000),V(55.60400,1.83100,0.00000),V(55.46600,1.90500,0.00000),V(55.34400,2.00400,0.00000),V(55.24500,2.12600,0.00000),V(55.17100,2.26400,0.00000),V(55.12500,2.41400,0.00000),V(55.11000,2.57000,0.00000),V(55.12500,2.72600,0.00000),V(55.17100,2.87600,0.00000),V(55.24500,3.01400,0.00000),V(55.34400,3.13600,0.00000),V(55.46600,3.23500,0.00000),V(55.60400,3.30900,0.00000),V(55.75400,3.35500,0.00000),V(55.91000,3.37000,0.00000),V(56.06600,3.35500,0.00000),V(56.21600,3.30900,0.00000),V(56.35400,3.23500,0.00000),V(56.47600,3.13600,0.00000),V(56.57500,3.01400,0.00000),V(56.64900,2.87600,0.00000),V(56.69500,2.72600,0.00000),V(56.71000,2.57000,0.00000),V(56.69500,2.41400,0.00000),V(56.64900,2.26400,0.00000),V(56.57500,2.12600,0.00000),V(56.47600,2.00400,0.00000),V(56.35400,1.90500,0.00000),V(56.21600,1.83100,0.00000),V(56.06600,1.78500,0.00000)])]).extrude(V(0,0,0.01000)))
_s.append(Part.Face([_poly([V(58.60600,1.78500,0.00000),V(58.45000,1.77000,0.00000),V(58.29400,1.78500,0.00000),V(58.14400,1.83100,0.00000),V(58.00600,1.90500,0.00000),V(57.88400,2.00400,0.00000),V(57.78500,2.12600,0.00000),V(57.71100,2.26400,0.00000),V(57.66500,2.41400,0.00000),V(57.65000,2.57000,0.00000),V(57.66500,2.72600,0.00000),V(57.71100,2.87600,0.00000),V(57.78500,3.01400,0.00000),V(57.88400,3.13600,0.00000),V(58.00600,3.23500,0.00000),V(58.14400,3.30900,0.00000),V(58.29400,3.35500,0.00000),V(58.45000,3.37000,0.00000),V(58.60600,3.35500,0.00000),V(58.75600,3.30900,0.00000),V(58.89400,3.23500,0.00000),V(59.01600,3.13600,0.00000),V(59.11500,3.01400,0.00000),V(59.18900,2.87600,0.00000),V(59.23500,2.72600,0.00000),V(59.25000,2.57000,0.00000),V(59.23500,2.41400,0.00000),V(59.18900,2.26400,0.00000),V(59.11500,2.12600,0.00000),V(59.01600,2.00400,0.00000),V(58.89400,1.90500,0.00000),V(58.75600,1.83100,0.00000),V(58.60600,1.78500,0.00000)])]).extrude(V(0,0,0.01000)))
_s.append(Part.Face([_poly([V(61.29600,1.83100,0.00000),V(61.14600,1.78500,0.00000),V(60.99000,1.77000,0.00000),V(60.83400,1.78500,0.00000),V(60.68400,1.83100,0.00000),V(60.54600,1.90500,0.00000),V(60.42400,2.00400,0.00000),V(60.32500,2.12600,0.00000),V(60.25100,2.26400,0.00000),V(60.20500,2.41400,0.00000),V(60.19000,2.57000,0.00000),V(60.20500,2.72600,0.00000),V(60.25100,2.87600,0.00000),V(60.32500,3.01400,0.00000),V(60.42400,3.13600,0.00000),V(60.54600,3.23500,0.00000),V(60.68400,3.30900,0.00000),V(60.83400,3.35500,0.00000),V(60.99000,3.37000,0.00000),V(61.14600,3.35500,0.00000),V(61.29600,3.30900,0.00000),V(61.43400,3.23500,0.00000),V(61.55600,3.13600,0.00000),V(61.65500,3.01400,0.00000),V(61.72900,2.87600,0.00000),V(61.77500,2.72600,0.00000),V(61.79000,2.57000,0.00000),V(61.77500,2.41400,0.00000),V(61.72900,2.26400,0.00000),V(61.65500,2.12600,0.00000),V(61.55600,2.00400,0.00000),V(61.43400,1.90500,0.00000),V(61.29600,1.83100,0.00000)])]).extrude(V(0,0,0.01000)))
_s.append(Part.Face([_poly([V(63.68600,1.78500,0.00000),V(63.53000,1.77000,0.00000),V(63.37400,1.78500,0.00000),V(63.22400,1.83100,0.00000),V(63.08600,1.90500,0.00000),V(62.96400,2.00400,0.00000),V(62.86500,2.12600,0.00000),V(62.79100,2.26400,0.00000),V(62.74500,2.41400,0.00000),V(62.73000,2.57000,0.00000),V(62.74500,2.72600,0.00000),V(62.79100,2.87600,0.00000),V(62.86500,3.01400,0.00000),V(62.96400,3.13600,0.00000),V(63.08600,3.23500,0.00000),V(63.22400,3.30900,0.00000),V(63.37400,3.35500,0.00000),V(63.53000,3.37000,0.00000),V(63.68600,3.35500,0.00000),V(63.83600,3.30900,0.00000),V(63.97400,3.23500,0.00000),V(64.09600,3.13600,0.00000),V(64.19500,3.01400,0.00000),V(64.26900,2.87600,0.00000),V(64.31500,2.72600,0.00000),V(64.33000,2.57000,0.00000),V(64.31500,2.41400,0.00000),V(64.26900,2.26400,0.00000),V(64.19500,2.12600,0.00000),V(64.09600,2.00400,0.00000),V(63.97400,1.90500,0.00000),V(63.83600,1.83100,0.00000),V(63.68600,1.78500,0.00000)])]).extrude(V(0,0,0.01000)))
_s.append(Part.Face([_poly([V(66.22600,1.78500,0.00000),V(66.07000,1.77000,0.00000),V(65.91400,1.78500,0.00000),V(65.76400,1.83100,0.00000),V(65.62600,1.90500,0.00000),V(65.50400,2.00400,0.00000),V(65.40500,2.12600,0.00000),V(65.33100,2.26400,0.00000),V(65.28500,2.41400,0.00000),V(65.27000,2.57000,0.00000),V(65.28500,2.72600,0.00000),V(65.33100,2.87600,0.00000),V(65.40500,3.01400,0.00000),V(65.50400,3.13600,0.00000),V(65.62600,3.23500,0.00000),V(65.76400,3.30900,0.00000),V(65.91400,3.35500,0.00000),V(66.07000,3.37000,0.00000),V(66.22600,3.35500,0.00000),V(66.37600,3.30900,0.00000),V(66.51400,3.23500,0.00000),V(66.63600,3.13600,0.00000),V(66.73500,3.01400,0.00000),V(66.80900,2.87600,0.00000),V(66.85500,2.72600,0.00000),V(66.87000,2.57000,0.00000),V(66.85500,2.41400,0.00000),V(66.80900,2.26400,0.00000),V(66.73500,2.12600,0.00000),V(66.63600,2.00400,0.00000),V(66.51400,1.90500,0.00000),V(66.37600,1.83100,0.00000),V(66.22600,1.78500,0.00000)])]).extrude(V(0,0,0.01000)))
_s.append(Part.Face([_poly([V(68.91600,1.83100,0.00000),V(68.76600,1.78500,0.00000),V(68.61000,1.77000,0.00000),V(68.45400,1.78500,0.00000),V(68.30400,1.83100,0.00000),V(68.16600,1.90500,0.00000),V(68.04400,2.00400,0.00000),V(67.94500,2.12600,0.00000),V(67.87100,2.26400,0.00000),V(67.82500,2.41400,0.00000),V(67.81000,2.57000,0.00000),V(67.82500,2.72600,0.00000),V(67.87100,2.87600,0.00000),V(67.94500,3.01400,0.00000),V(68.04400,3.13600,0.00000),V(68.16600,3.23500,0.00000),V(68.30400,3.30900,0.00000),V(68.45400,3.35500,0.00000),V(68.61000,3.37000,0.00000),V(68.76600,3.35500,0.00000),V(68.91600,3.30900,0.00000),V(69.05400,3.23500,0.00000),V(69.17600,3.13600,0.00000),V(69.27500,3.01400,0.00000),V(69.34900,2.87600,0.00000),V(69.39500,2.72600,0.00000),V(69.41000,2.57000,0.00000),V(69.39500,2.41400,0.00000),V(69.34900,2.26400,0.00000),V(69.27500,2.12600,0.00000),V(69.17600,2.00400,0.00000),V(69.05400,1.90500,0.00000),V(68.91600,1.83100,0.00000)])]).extrude(V(0,0,0.01000)))
_s.append(Part.Face([_poly([V(71.30600,1.78500,0.00000),V(71.15000,1.77000,0.00000),V(70.99400,1.78500,0.00000),V(70.84400,1.83100,0.00000),V(70.70600,1.90500,0.00000),V(70.58400,2.00400,0.00000),V(70.48500,2.12600,0.00000),V(70.41100,2.26400,0.00000),V(70.36500,2.41400,0.00000),V(70.35000,2.57000,0.00000),V(70.36500,2.72600,0.00000),V(70.41100,2.87600,0.00000),V(70.48500,3.01400,0.00000),V(70.58400,3.13600,0.00000),V(70.70600,3.23500,0.00000),V(70.84400,3.30900,0.00000),V(70.99400,3.35500,0.00000),V(71.15000,3.37000,0.00000),V(71.30600,3.35500,0.00000),V(71.45600,3.30900,0.00000),V(71.59400,3.23500,0.00000),V(71.71600,3.13600,0.00000),V(71.81500,3.01400,0.00000),V(71.88900,2.87600,0.00000),V(71.93500,2.72600,0.00000),V(71.95000,2.57000,0.00000),V(71.93500,2.41400,0.00000),V(71.88900,2.26400,0.00000),V(71.81500,2.12600,0.00000),V(71.71600,2.00400,0.00000),V(71.59400,1.90500,0.00000),V(71.45600,1.83100,0.00000),V(71.30600,1.78500,0.00000)])]).extrude(V(0,0,0.01000)))
_s.append(Part.Face([_poly([V(73.84600,1.78500,0.00000),V(73.69000,1.77000,0.00000),V(73.53400,1.78500,0.00000),V(73.38400,1.83100,0.00000),V(73.24600,1.90500,0.00000),V(73.12400,2.00400,0.00000),V(73.02500,2.12600,0.00000),V(72.95100,2.26400,0.00000),V(72.90500,2.41400,0.00000),V(72.89000,2.57000,0.00000),V(72.90500,2.72600,0.00000),V(72.95100,2.87600,0.00000),V(73.02500,3.01400,0.00000),V(73.12400,3.13600,0.00000),V(73.24600,3.23500,0.00000),V(73.38400,3.30900,0.00000),V(73.53400,3.35500,0.00000),V(73.69000,3.37000,0.00000),V(73.84600,3.35500,0.00000),V(73.99600,3.30900,0.00000),V(74.13400,3.23500,0.00000),V(74.25600,3.13600,0.00000),V(74.35500,3.01400,0.00000),V(74.42900,2.87600,0.00000),V(74.47500,2.72600,0.00000),V(74.49000,2.57000,0.00000),V(74.47500,2.41400,0.00000),V(74.42900,2.26400,0.00000),V(74.35500,2.12600,0.00000),V(74.25600,2.00400,0.00000),V(74.13400,1.90500,0.00000),V(73.99600,1.83100,0.00000),V(73.84600,1.78500,0.00000)])]).extrude(V(0,0,0.01000)))
_s.append(Part.Face([_poly([V(76.53600,1.83100,0.00000),V(76.38600,1.78500,0.00000),V(76.23000,1.77000,0.00000),V(76.07400,1.78500,0.00000),V(75.92400,1.83100,0.00000),V(75.78600,1.90500,0.00000),V(75.66400,2.00400,0.00000),V(75.56500,2.12600,0.00000),V(75.49100,2.26400,0.00000),V(75.44500,2.41400,0.00000),V(75.43000,2.57000,0.00000),V(75.44500,2.72600,0.00000),V(75.49100,2.87600,0.00000),V(75.56500,3.01400,0.00000),V(75.66400,3.13600,0.00000),V(75.78600,3.23500,0.00000),V(75.92400,3.30900,0.00000),V(76.07400,3.35500,0.00000),V(76.23000,3.37000,0.00000),V(76.38600,3.35500,0.00000),V(76.53600,3.30900,0.00000),V(76.67400,3.23500,0.00000),V(76.79600,3.13600,0.00000),V(76.89500,3.01400,0.00000),V(76.96900,2.87600,0.00000),V(77.01500,2.72600,0.00000),V(77.03000,2.57000,0.00000),V(77.01500,2.41400,0.00000),V(76.96900,2.26400,0.00000),V(76.89500,2.12600,0.00000),V(76.79600,2.00400,0.00000),V(76.67400,1.90500,0.00000),V(76.53600,1.83100,0.00000)])]).extrude(V(0,0,0.01000)))
_s.append(Part.Face([_poly([V(90.92600,1.78500,0.00000),V(90.77000,1.77000,0.00000),V(90.61400,1.78500,0.00000),V(90.46400,1.83100,0.00000),V(90.32600,1.90500,0.00000),V(90.20400,2.00400,0.00000),V(90.10500,2.12600,0.00000),V(90.03100,2.26400,0.00000),V(89.98500,2.41400,0.00000),V(89.97000,2.57000,0.00000),V(89.98500,2.72600,0.00000),V(90.03100,2.87600,0.00000),V(90.10500,3.01400,0.00000),V(90.20400,3.13600,0.00000),V(90.32600,3.23500,0.00000),V(90.46400,3.30900,0.00000),V(90.61400,3.35500,0.00000),V(90.77000,3.37000,0.00000),V(90.92600,3.35500,0.00000),V(91.07600,3.30900,0.00000),V(91.21400,3.23500,0.00000),V(91.33600,3.13600,0.00000),V(91.43500,3.01400,0.00000),V(91.50900,2.87600,0.00000),V(91.55500,2.72600,0.00000),V(91.57000,2.57000,0.00000),V(91.55500,2.41400,0.00000),V(91.50900,2.26400,0.00000),V(91.43500,2.12600,0.00000),V(91.33600,2.00400,0.00000),V(91.21400,1.90500,0.00000),V(91.07600,1.83100,0.00000),V(90.92600,1.78500,0.00000)])]).extrude(V(0,0,0.01000)))
_s.append(Part.Face([_poly([V(93.46600,1.78500,0.00000),V(93.31000,1.77000,0.00000),V(93.15400,1.78500,0.00000),V(93.00400,1.83100,0.00000),V(92.86600,1.90500,0.00000),V(92.74400,2.00400,0.00000),V(92.64500,2.12600,0.00000),V(92.57100,2.26400,0.00000),V(92.52500,2.41400,0.00000),V(92.51000,2.57000,0.00000),V(92.52500,2.72600,0.00000),V(92.57100,2.87600,0.00000),V(92.64500,3.01400,0.00000),V(92.74400,3.13600,0.00000),V(92.86600,3.23500,0.00000),V(93.00400,3.30900,0.00000),V(93.15400,3.35500,0.00000),V(93.31000,3.37000,0.00000),V(93.46600,3.35500,0.00000),V(93.61600,3.30900,0.00000),V(93.75400,3.23500,0.00000),V(93.87600,3.13600,0.00000),V(93.97500,3.01400,0.00000),V(94.04900,2.87600,0.00000),V(94.09500,2.72600,0.00000),V(94.11000,2.57000,0.00000),V(94.09500,2.41400,0.00000),V(94.04900,2.26400,0.00000),V(93.97500,2.12600,0.00000),V(93.87600,2.00400,0.00000),V(93.75400,1.90500,0.00000),V(93.61600,1.83100,0.00000),V(93.46600,1.78500,0.00000)])]).extrude(V(0,0,0.01000)))
_s.append(Part.Face([_poly([V(96.15600,1.83100,0.00000),V(96.00600,1.78500,0.00000),V(95.85000,1.77000,0.00000),V(95.69400,1.78500,0.00000),V(95.54400,1.83100,0.00000),V(95.40600,1.90500,0.00000),V(95.28400,2.00400,0.00000),V(95.18500,2.12600,0.00000),V(95.11100,2.26400,0.00000),V(95.06500,2.41400,0.00000),V(95.05000,2.57000,0.00000),V(95.06500,2.72600,0.00000),V(95.11100,2.87600,0.00000),V(95.18500,3.01400,0.00000),V(95.28400,3.13600,0.00000),V(95.40600,3.23500,0.00000),V(95.54400,3.30900,0.00000),V(95.69400,3.35500,0.00000),V(95.85000,3.37000,0.00000),V(96.00600,3.35500,0.00000),V(96.15600,3.30900,0.00000),V(96.29400,3.23500,0.00000),V(96.41600,3.13600,0.00000),V(96.51500,3.01400,0.00000),V(96.58900,2.87600,0.00000),V(96.63500,2.72600,0.00000),V(96.65000,2.57000,0.00000),V(96.63500,2.41400,0.00000),V(96.58900,2.26400,0.00000),V(96.51500,2.12600,0.00000),V(96.41600,2.00400,0.00000),V(96.29400,1.90500,0.00000),V(96.15600,1.83100,0.00000)])]).extrude(V(0,0,0.01000)))
_s.append(Part.Face([_poly([V(98.54600,1.78500,0.00000),V(98.39000,1.77000,0.00000),V(98.23400,1.78500,0.00000),V(98.08400,1.83100,0.00000),V(97.94600,1.90500,0.00000),V(97.82400,2.00400,0.00000),V(97.72500,2.12600,0.00000),V(97.65100,2.26400,0.00000),V(97.60500,2.41400,0.00000),V(97.59000,2.57000,0.00000),V(97.60500,2.72600,0.00000),V(97.65100,2.87600,0.00000),V(97.72500,3.01400,0.00000),V(97.82400,3.13600,0.00000),V(97.94600,3.23500,0.00000),V(98.08400,3.30900,0.00000),V(98.23400,3.35500,0.00000),V(98.39000,3.37000,0.00000),V(98.54600,3.35500,0.00000),V(98.69600,3.30900,0.00000),V(98.83400,3.23500,0.00000),V(98.95600,3.13600,0.00000),V(99.05500,3.01400,0.00000),V(99.12900,2.87600,0.00000),V(99.17500,2.72600,0.00000),V(99.19000,2.57000,0.00000),V(99.17500,2.41400,0.00000),V(99.12900,2.26400,0.00000),V(99.05500,2.12600,0.00000),V(98.95600,2.00400,0.00000),V(98.83400,1.90500,0.00000),V(98.69600,1.83100,0.00000),V(98.54600,1.78500,0.00000)])]).extrude(V(0,0,0.01000)))
_s.append(Part.Face([_poly([V(101.08600,1.78500,0.00000),V(100.93000,1.77000,0.00000),V(100.77400,1.78500,0.00000),V(100.62400,1.83100,0.00000),V(100.48600,1.90500,0.00000),V(100.36400,2.00400,0.00000),V(100.26500,2.12600,0.00000),V(100.19100,2.26400,0.00000),V(100.14500,2.41400,0.00000),V(100.13000,2.57000,0.00000),V(100.14500,2.72600,0.00000),V(100.19100,2.87600,0.00000),V(100.26500,3.01400,0.00000),V(100.36400,3.13600,0.00000),V(100.48600,3.23500,0.00000),V(100.62400,3.30900,0.00000),V(100.77400,3.35500,0.00000),V(100.93000,3.37000,0.00000),V(101.08600,3.35500,0.00000),V(101.23600,3.30900,0.00000),V(101.37400,3.23500,0.00000),V(101.49600,3.13600,0.00000),V(101.59500,3.01400,0.00000),V(101.66900,2.87600,0.00000),V(101.71500,2.72600,0.00000),V(101.73000,2.57000,0.00000),V(101.71500,2.41400,0.00000),V(101.66900,2.26400,0.00000),V(101.59500,2.12600,0.00000),V(101.49600,2.00400,0.00000),V(101.37400,1.90500,0.00000),V(101.23600,1.83100,0.00000),V(101.08600,1.78500,0.00000)])]).extrude(V(0,0,0.01000)))
_s.append(Part.Face([_poly([V(53.67600,24.69100,0.00000),V(53.52600,24.64500,0.00000),V(53.37000,24.63000,0.00000),V(53.21400,24.64500,0.00000),V(53.06400,24.69100,0.00000),V(52.92600,24.76500,0.00000),V(52.80400,24.86400,0.00000),V(52.70500,24.98600,0.00000),V(52.63100,25.12400,0.00000),V(52.58500,25.27400,0.00000),V(52.57000,25.43000,0.00000),V(52.58500,25.58600,0.00000),V(52.63100,25.73600,0.00000),V(52.70500,25.87400,0.00000),V(52.80400,25.99600,0.00000),V(52.92600,26.09500,0.00000),V(53.06400,26.16900,0.00000),V(53.21400,26.21500,0.00000),V(53.37000,26.23000,0.00000),V(53.52600,26.21500,0.00000),V(53.67600,26.16900,0.00000),V(53.81400,26.09500,0.00000),V(53.93600,25.99600,0.00000),V(54.03500,25.87400,0.00000),V(54.10900,25.73600,0.00000),V(54.15500,25.58600,0.00000),V(54.17000,25.43000,0.00000),V(54.15500,25.27400,0.00000),V(54.10900,25.12400,0.00000),V(54.03500,24.98600,0.00000),V(53.93600,24.86400,0.00000),V(53.81400,24.76500,0.00000),V(53.67600,24.69100,0.00000)])]).extrude(V(0,0,0.01000)))
_s.append(Part.Face([_poly([V(56.21600,24.69100,0.00000),V(56.06600,24.64500,0.00000),V(55.91000,24.63000,0.00000),V(55.75400,24.64500,0.00000),V(55.60400,24.69100,0.00000),V(55.46600,24.76500,0.00000),V(55.34400,24.86400,0.00000),V(55.24500,24.98600,0.00000),V(55.17100,25.12400,0.00000),V(55.12500,25.27400,0.00000),V(55.11000,25.43000,0.00000),V(55.12500,25.58600,0.00000),V(55.17100,25.73600,0.00000),V(55.24500,25.87400,0.00000),V(55.34400,25.99600,0.00000),V(55.46600,26.09500,0.00000),V(55.60400,26.16900,0.00000),V(55.75400,26.21500,0.00000),V(55.91000,26.23000,0.00000),V(56.06600,26.21500,0.00000),V(56.21600,26.16900,0.00000),V(56.35400,26.09500,0.00000),V(56.47600,25.99600,0.00000),V(56.57500,25.87400,0.00000),V(56.64900,25.73600,0.00000),V(56.69500,25.58600,0.00000),V(56.71000,25.43000,0.00000),V(56.69500,25.27400,0.00000),V(56.64900,25.12400,0.00000),V(56.57500,24.98600,0.00000),V(56.47600,24.86400,0.00000),V(56.35400,24.76500,0.00000),V(56.21600,24.69100,0.00000)])]).extrude(V(0,0,0.01000)))
_s.append(Part.Face([_poly([V(58.75600,24.69100,0.00000),V(58.60600,24.64500,0.00000),V(58.45000,24.63000,0.00000),V(58.29400,24.64500,0.00000),V(58.14400,24.69100,0.00000),V(58.00600,24.76500,0.00000),V(57.88400,24.86400,0.00000),V(57.78500,24.98600,0.00000),V(57.71100,25.12400,0.00000),V(57.66500,25.27400,0.00000),V(57.65000,25.43000,0.00000),V(57.66500,25.58600,0.00000),V(57.71100,25.73600,0.00000),V(57.78500,25.87400,0.00000),V(57.88400,25.99600,0.00000),V(58.00600,26.09500,0.00000),V(58.14400,26.16900,0.00000),V(58.29400,26.21500,0.00000),V(58.45000,26.23000,0.00000),V(58.60600,26.21500,0.00000),V(58.75600,26.16900,0.00000),V(58.89400,26.09500,0.00000),V(59.01600,25.99600,0.00000),V(59.11500,25.87400,0.00000),V(59.18900,25.73600,0.00000),V(59.23500,25.58600,0.00000),V(59.25000,25.43000,0.00000),V(59.23500,25.27400,0.00000),V(59.18900,25.12400,0.00000),V(59.11500,24.98600,0.00000),V(59.01600,24.86400,0.00000),V(58.89400,24.76500,0.00000),V(58.75600,24.69100,0.00000)])]).extrude(V(0,0,0.01000)))
_s.append(Part.Face([_poly([V(61.14600,24.64500,0.00000),V(60.99000,24.63000,0.00000),V(60.83400,24.64500,0.00000),V(60.68400,24.69100,0.00000),V(60.54600,24.76500,0.00000),V(60.42400,24.86400,0.00000),V(60.32500,24.98600,0.00000),V(60.25100,25.12400,0.00000),V(60.20500,25.27400,0.00000),V(60.19000,25.43000,0.00000),V(60.20500,25.58600,0.00000),V(60.25100,25.73600,0.00000),V(60.32500,25.87400,0.00000),V(60.42400,25.99600,0.00000),V(60.54600,26.09500,0.00000),V(60.68400,26.16900,0.00000),V(60.83400,26.21500,0.00000),V(60.99000,26.23000,0.00000),V(61.14600,26.21500,0.00000),V(61.29600,26.16900,0.00000),V(61.43400,26.09500,0.00000),V(61.55600,25.99600,0.00000),V(61.65500,25.87400,0.00000),V(61.72900,25.73600,0.00000),V(61.77500,25.58600,0.00000),V(61.79000,25.43000,0.00000),V(61.77500,25.27400,0.00000),V(61.72900,25.12400,0.00000),V(61.65500,24.98600,0.00000),V(61.55600,24.86400,0.00000),V(61.43400,24.76500,0.00000),V(61.29600,24.69100,0.00000),V(61.14600,24.64500,0.00000)])]).extrude(V(0,0,0.01000)))
_s.append(Part.Face([_poly([V(63.68600,24.64500,0.00000),V(63.53000,24.63000,0.00000),V(63.37400,24.64500,0.00000),V(63.22400,24.69100,0.00000),V(63.08600,24.76500,0.00000),V(62.96400,24.86400,0.00000),V(62.86500,24.98600,0.00000),V(62.79100,25.12400,0.00000),V(62.74500,25.27400,0.00000),V(62.73000,25.43000,0.00000),V(62.74500,25.58600,0.00000),V(62.79100,25.73600,0.00000),V(62.86500,25.87400,0.00000),V(62.96400,25.99600,0.00000),V(63.08600,26.09500,0.00000),V(63.22400,26.16900,0.00000),V(63.37400,26.21500,0.00000),V(63.53000,26.23000,0.00000),V(63.68600,26.21500,0.00000),V(63.83600,26.16900,0.00000),V(63.97400,26.09500,0.00000),V(64.09600,25.99600,0.00000),V(64.19500,25.87400,0.00000),V(64.26900,25.73600,0.00000),V(64.31500,25.58600,0.00000),V(64.33000,25.43000,0.00000),V(64.31500,25.27400,0.00000),V(64.26900,25.12400,0.00000),V(64.19500,24.98600,0.00000),V(64.09600,24.86400,0.00000),V(63.97400,24.76500,0.00000),V(63.83600,24.69100,0.00000),V(63.68600,24.64500,0.00000)])]).extrude(V(0,0,0.01000)))
_s.append(Part.Face([_poly([V(66.37600,24.69100,0.00000),V(66.22600,24.64500,0.00000),V(66.07000,24.63000,0.00000),V(65.91400,24.64500,0.00000),V(65.76400,24.69100,0.00000),V(65.62600,24.76500,0.00000),V(65.50400,24.86400,0.00000),V(65.40500,24.98600,0.00000),V(65.33100,25.12400,0.00000),V(65.28500,25.27400,0.00000),V(65.27000,25.43000,0.00000),V(65.28500,25.58600,0.00000),V(65.33100,25.73600,0.00000),V(65.40500,25.87400,0.00000),V(65.50400,25.99600,0.00000),V(65.62600,26.09500,0.00000),V(65.76400,26.16900,0.00000),V(65.91400,26.21500,0.00000),V(66.07000,26.23000,0.00000),V(66.22600,26.21500,0.00000),V(66.37600,26.16900,0.00000),V(66.51400,26.09500,0.00000),V(66.63600,25.99600,0.00000),V(66.73500,25.87400,0.00000),V(66.80900,25.73600,0.00000),V(66.85500,25.58600,0.00000),V(66.87000,25.43000,0.00000),V(66.85500,25.27400,0.00000),V(66.80900,25.12400,0.00000),V(66.73500,24.98600,0.00000),V(66.63600,24.86400,0.00000),V(66.51400,24.76500,0.00000),V(66.37600,24.69100,0.00000)])]).extrude(V(0,0,0.01000)))
_s.append(Part.Face([_poly([V(68.76600,24.64500,0.00000),V(68.61000,24.63000,0.00000),V(68.45400,24.64500,0.00000),V(68.30400,24.69100,0.00000),V(68.16600,24.76500,0.00000),V(68.04400,24.86400,0.00000),V(67.94500,24.98600,0.00000),V(67.87100,25.12400,0.00000),V(67.82500,25.27400,0.00000),V(67.81000,25.43000,0.00000),V(67.82500,25.58600,0.00000),V(67.87100,25.73600,0.00000),V(67.94500,25.87400,0.00000),V(68.04400,25.99600,0.00000),V(68.16600,26.09500,0.00000),V(68.30400,26.16900,0.00000),V(68.45400,26.21500,0.00000),V(68.61000,26.23000,0.00000),V(68.76600,26.21500,0.00000),V(68.91600,26.16900,0.00000),V(69.05400,26.09500,0.00000),V(69.17600,25.99600,0.00000),V(69.27500,25.87400,0.00000),V(69.34900,25.73600,0.00000),V(69.39500,25.58600,0.00000),V(69.41000,25.43000,0.00000),V(69.39500,25.27400,0.00000),V(69.34900,25.12400,0.00000),V(69.27500,24.98600,0.00000),V(69.17600,24.86400,0.00000),V(69.05400,24.76500,0.00000),V(68.91600,24.69100,0.00000),V(68.76600,24.64500,0.00000)])]).extrude(V(0,0,0.01000)))
_s.append(Part.Face([_poly([V(71.30600,24.64500,0.00000),V(71.15000,24.63000,0.00000),V(70.99400,24.64500,0.00000),V(70.84400,24.69100,0.00000),V(70.70600,24.76500,0.00000),V(70.58400,24.86400,0.00000),V(70.48500,24.98600,0.00000),V(70.41100,25.12400,0.00000),V(70.36500,25.27400,0.00000),V(70.35000,25.43000,0.00000),V(70.36500,25.58600,0.00000),V(70.41100,25.73600,0.00000),V(70.48500,25.87400,0.00000),V(70.58400,25.99600,0.00000),V(70.70600,26.09500,0.00000),V(70.84400,26.16900,0.00000),V(70.99400,26.21500,0.00000),V(71.15000,26.23000,0.00000),V(71.30600,26.21500,0.00000),V(71.45600,26.16900,0.00000),V(71.59400,26.09500,0.00000),V(71.71600,25.99600,0.00000),V(71.81500,25.87400,0.00000),V(71.88900,25.73600,0.00000),V(71.93500,25.58600,0.00000),V(71.95000,25.43000,0.00000),V(71.93500,25.27400,0.00000),V(71.88900,25.12400,0.00000),V(71.81500,24.98600,0.00000),V(71.71600,24.86400,0.00000),V(71.59400,24.76500,0.00000),V(71.45600,24.69100,0.00000),V(71.30600,24.64500,0.00000)])]).extrude(V(0,0,0.01000)))
_s.append(Part.Face([_poly([V(73.99600,24.69100,0.00000),V(73.84600,24.64500,0.00000),V(73.69000,24.63000,0.00000),V(73.53400,24.64500,0.00000),V(73.38400,24.69100,0.00000),V(73.24600,24.76500,0.00000),V(73.12400,24.86400,0.00000),V(73.02500,24.98600,0.00000),V(72.95100,25.12400,0.00000),V(72.90500,25.27400,0.00000),V(72.89000,25.43000,0.00000),V(72.90500,25.58600,0.00000),V(72.95100,25.73600,0.00000),V(73.02500,25.87400,0.00000),V(73.12400,25.99600,0.00000),V(73.24600,26.09500,0.00000),V(73.38400,26.16900,0.00000),V(73.53400,26.21500,0.00000),V(73.69000,26.23000,0.00000),V(73.84600,26.21500,0.00000),V(73.99600,26.16900,0.00000),V(74.13400,26.09500,0.00000),V(74.25600,25.99600,0.00000),V(74.35500,25.87400,0.00000),V(74.42900,25.73600,0.00000),V(74.47500,25.58600,0.00000),V(74.49000,25.43000,0.00000),V(74.47500,25.27400,0.00000),V(74.42900,25.12400,0.00000),V(74.35500,24.98600,0.00000),V(74.25600,24.86400,0.00000),V(74.13400,24.76500,0.00000),V(73.99600,24.69100,0.00000)])]).extrude(V(0,0,0.01000)))
_s.append(Part.Face([_poly([V(76.38600,24.64500,0.00000),V(76.23000,24.63000,0.00000),V(76.07400,24.64500,0.00000),V(75.92400,24.69100,0.00000),V(75.78600,24.76500,0.00000),V(75.66400,24.86400,0.00000),V(75.56500,24.98600,0.00000),V(75.49100,25.12400,0.00000),V(75.44500,25.27400,0.00000),V(75.43000,25.43000,0.00000),V(75.44500,25.58600,0.00000),V(75.49100,25.73600,0.00000),V(75.56500,25.87400,0.00000),V(75.66400,25.99600,0.00000),V(75.78600,26.09500,0.00000),V(75.92400,26.16900,0.00000),V(76.07400,26.21500,0.00000),V(76.23000,26.23000,0.00000),V(76.38600,26.21500,0.00000),V(76.53600,26.16900,0.00000),V(76.67400,26.09500,0.00000),V(76.79600,25.99600,0.00000),V(76.89500,25.87400,0.00000),V(76.96900,25.73600,0.00000),V(77.01500,25.58600,0.00000),V(77.03000,25.43000,0.00000),V(77.01500,25.27400,0.00000),V(76.96900,25.12400,0.00000),V(76.89500,24.98600,0.00000),V(76.79600,24.86400,0.00000),V(76.67400,24.76500,0.00000),V(76.53600,24.69100,0.00000),V(76.38600,24.64500,0.00000)])]).extrude(V(0,0,0.01000)))
_s.append(Part.Face([_poly([V(90.92600,24.64500,0.00000),V(90.77000,24.63000,0.00000),V(90.61400,24.64500,0.00000),V(90.46400,24.69100,0.00000),V(90.32600,24.76500,0.00000),V(90.20400,24.86400,0.00000),V(90.10500,24.98600,0.00000),V(90.03100,25.12400,0.00000),V(89.98500,25.27400,0.00000),V(89.97000,25.43000,0.00000),V(89.98500,25.58600,0.00000),V(90.03100,25.73600,0.00000),V(90.10500,25.87400,0.00000),V(90.20400,25.99600,0.00000),V(90.32600,26.09500,0.00000),V(90.46400,26.16900,0.00000),V(90.61400,26.21500,0.00000),V(90.77000,26.23000,0.00000),V(90.92600,26.21500,0.00000),V(91.07600,26.16900,0.00000),V(91.21400,26.09500,0.00000),V(91.33600,25.99600,0.00000),V(91.43500,25.87400,0.00000),V(91.50900,25.73600,0.00000),V(91.55500,25.58600,0.00000),V(91.57000,25.43000,0.00000),V(91.55500,25.27400,0.00000),V(91.50900,25.12400,0.00000),V(91.43500,24.98600,0.00000),V(91.33600,24.86400,0.00000),V(91.21400,24.76500,0.00000),V(91.07600,24.69100,0.00000),V(90.92600,24.64500,0.00000)])]).extrude(V(0,0,0.01000)))
_s.append(Part.Face([_poly([V(93.61600,24.69100,0.00000),V(93.46600,24.64500,0.00000),V(93.31000,24.63000,0.00000),V(93.15400,24.64500,0.00000),V(93.00400,24.69100,0.00000),V(92.86600,24.76500,0.00000),V(92.74400,24.86400,0.00000),V(92.64500,24.98600,0.00000),V(92.57100,25.12400,0.00000),V(92.52500,25.27400,0.00000),V(92.51000,25.43000,0.00000),V(92.52500,25.58600,0.00000),V(92.57100,25.73600,0.00000),V(92.64500,25.87400,0.00000),V(92.74400,25.99600,0.00000),V(92.86600,26.09500,0.00000),V(93.00400,26.16900,0.00000),V(93.15400,26.21500,0.00000),V(93.31000,26.23000,0.00000),V(93.46600,26.21500,0.00000),V(93.61600,26.16900,0.00000),V(93.75400,26.09500,0.00000),V(93.87600,25.99600,0.00000),V(93.97500,25.87400,0.00000),V(94.04900,25.73600,0.00000),V(94.09500,25.58600,0.00000),V(94.11000,25.43000,0.00000),V(94.09500,25.27400,0.00000),V(94.04900,25.12400,0.00000),V(93.97500,24.98600,0.00000),V(93.87600,24.86400,0.00000),V(93.75400,24.76500,0.00000),V(93.61600,24.69100,0.00000)])]).extrude(V(0,0,0.01000)))
_s.append(Part.Face([_poly([V(96.15600,24.69100,0.00000),V(96.00600,24.64500,0.00000),V(95.85000,24.63000,0.00000),V(95.69400,24.64500,0.00000),V(95.54400,24.69100,0.00000),V(95.40600,24.76500,0.00000),V(95.28400,24.86400,0.00000),V(95.18500,24.98600,0.00000),V(95.11100,25.12400,0.00000),V(95.06500,25.27400,0.00000),V(95.05000,25.43000,0.00000),V(95.06500,25.58600,0.00000),V(95.11100,25.73600,0.00000),V(95.18500,25.87400,0.00000),V(95.28400,25.99600,0.00000),V(95.40600,26.09500,0.00000),V(95.54400,26.16900,0.00000),V(95.69400,26.21500,0.00000),V(95.85000,26.23000,0.00000),V(96.00600,26.21500,0.00000),V(96.15600,26.16900,0.00000),V(96.29400,26.09500,0.00000),V(96.41600,25.99600,0.00000),V(96.51500,25.87400,0.00000),V(96.58900,25.73600,0.00000),V(96.63500,25.58600,0.00000),V(96.65000,25.43000,0.00000),V(96.63500,25.27400,0.00000),V(96.58900,25.12400,0.00000),V(96.51500,24.98600,0.00000),V(96.41600,24.86400,0.00000),V(96.29400,24.76500,0.00000),V(96.15600,24.69100,0.00000)])]).extrude(V(0,0,0.01000)))
_s.append(Part.Face([_poly([V(98.69600,24.69100,0.00000),V(98.54600,24.64500,0.00000),V(98.39000,24.63000,0.00000),V(98.23400,24.64500,0.00000),V(98.08400,24.69100,0.00000),V(97.94600,24.76500,0.00000),V(97.82400,24.86400,0.00000),V(97.72500,24.98600,0.00000),V(97.65100,25.12400,0.00000),V(97.60500,25.27400,0.00000),V(97.59000,25.43000,0.00000),V(97.60500,25.58600,0.00000),V(97.65100,25.73600,0.00000),V(97.72500,25.87400,0.00000),V(97.82400,25.99600,0.00000),V(97.94600,26.09500,0.00000),V(98.08400,26.16900,0.00000),V(98.23400,26.21500,0.00000),V(98.39000,26.23000,0.00000),V(98.54600,26.21500,0.00000),V(98.69600,26.16900,0.00000),V(98.83400,26.09500,0.00000),V(98.95600,25.99600,0.00000),V(99.05500,25.87400,0.00000),V(99.12900,25.73600,0.00000),V(99.17500,25.58600,0.00000),V(99.19000,25.43000,0.00000),V(99.17500,25.27400,0.00000),V(99.12900,25.12400,0.00000),V(99.05500,24.98600,0.00000),V(98.95600,24.86400,0.00000),V(98.83400,24.76500,0.00000),V(98.69600,24.69100,0.00000)])]).extrude(V(0,0,0.01000)))
_s.append(Part.Face([_poly([V(101.08600,24.64500,0.00000),V(100.93000,24.63000,0.00000),V(100.77400,24.64500,0.00000),V(100.62400,24.69100,0.00000),V(100.48600,24.76500,0.00000),V(100.36400,24.86400,0.00000),V(100.26500,24.98600,0.00000),V(100.19100,25.12400,0.00000),V(100.14500,25.27400,0.00000),V(100.13000,25.43000,0.00000),V(100.14500,25.58600,0.00000),V(100.19100,25.73600,0.00000),V(100.26500,25.87400,0.00000),V(100.36400,25.99600,0.00000),V(100.48600,26.09500,0.00000),V(100.62400,26.16900,0.00000),V(100.77400,26.21500,0.00000),V(100.93000,26.23000,0.00000),V(101.08600,26.21500,0.00000),V(101.23600,26.16900,0.00000),V(101.37400,26.09500,0.00000),V(101.49600,25.99600,0.00000),V(101.59500,25.87400,0.00000),V(101.66900,25.73600,0.00000),V(101.71500,25.58600,0.00000),V(101.73000,25.43000,0.00000),V(101.71500,25.27400,0.00000),V(101.66900,25.12400,0.00000),V(101.59500,24.98600,0.00000),V(101.49600,24.86400,0.00000),V(101.37400,24.76500,0.00000),V(101.23600,24.69100,0.00000),V(101.08600,24.64500,0.00000)])]).extrude(V(0,0,0.01000)))
_s.append(Part.Face([_poly([V(103.62600,1.78500,0.00000),V(103.47000,1.77000,0.00000),V(103.31400,1.78500,0.00000),V(103.16400,1.83100,0.00000),V(103.02600,1.90500,0.00000),V(102.90400,2.00400,0.00000),V(102.80500,2.12600,0.00000),V(102.73100,2.26400,0.00000),V(102.68500,2.41400,0.00000),V(102.67000,2.57000,0.00000),V(102.68500,2.72600,0.00000),V(102.73100,2.87600,0.00000),V(102.80500,3.01400,0.00000),V(102.90400,3.13600,0.00000),V(103.02600,3.23500,0.00000),V(103.16400,3.30900,0.00000),V(103.31400,3.35500,0.00000),V(103.47000,3.37000,0.00000),V(103.62600,3.35500,0.00000),V(103.77600,3.30900,0.00000),V(103.91400,3.23500,0.00000),V(104.03600,3.13600,0.00000),V(104.13500,3.01400,0.00000),V(104.20900,2.87600,0.00000),V(104.25500,2.72600,0.00000),V(104.27000,2.57000,0.00000),V(104.25500,2.41400,0.00000),V(104.20900,2.26400,0.00000),V(104.13500,2.12600,0.00000),V(104.03600,2.00400,0.00000),V(103.91400,1.90500,0.00000),V(103.77600,1.83100,0.00000),V(103.62600,1.78500,0.00000)])]).extrude(V(0,0,0.01000)))
_s.append(Part.Face([_poly([V(106.31600,1.83100,0.00000),V(106.16600,1.78500,0.00000),V(106.01000,1.77000,0.00000),V(105.85400,1.78500,0.00000),V(105.70400,1.83100,0.00000),V(105.56600,1.90500,0.00000),V(105.44400,2.00400,0.00000),V(105.34500,2.12600,0.00000),V(105.27100,2.26400,0.00000),V(105.22500,2.41400,0.00000),V(105.21000,2.57000,0.00000),V(105.22500,2.72600,0.00000),V(105.27100,2.87600,0.00000),V(105.34500,3.01400,0.00000),V(105.44400,3.13600,0.00000),V(105.56600,3.23500,0.00000),V(105.70400,3.30900,0.00000),V(105.85400,3.35500,0.00000),V(106.01000,3.37000,0.00000),V(106.16600,3.35500,0.00000),V(106.31600,3.30900,0.00000),V(106.45400,3.23500,0.00000),V(106.57600,3.13600,0.00000),V(106.67500,3.01400,0.00000),V(106.74900,2.87600,0.00000),V(106.79500,2.72600,0.00000),V(106.81000,2.57000,0.00000),V(106.79500,2.41400,0.00000),V(106.74900,2.26400,0.00000),V(106.67500,2.12600,0.00000),V(106.57600,2.00400,0.00000),V(106.45400,1.90500,0.00000),V(106.31600,1.83100,0.00000)])]).extrude(V(0,0,0.01000)))
_s.append(Part.Face([_poly([V(108.70600,1.78500,0.00000),V(108.55000,1.77000,0.00000),V(108.39400,1.78500,0.00000),V(108.24400,1.83100,0.00000),V(108.10600,1.90500,0.00000),V(107.98400,2.00400,0.00000),V(107.88500,2.12600,0.00000),V(107.81100,2.26400,0.00000),V(107.76500,2.41400,0.00000),V(107.75000,2.57000,0.00000),V(107.76500,2.72600,0.00000),V(107.81100,2.87600,0.00000),V(107.88500,3.01400,0.00000),V(107.98400,3.13600,0.00000),V(108.10600,3.23500,0.00000),V(108.24400,3.30900,0.00000),V(108.39400,3.35500,0.00000),V(108.55000,3.37000,0.00000),V(108.70600,3.35500,0.00000),V(108.85600,3.30900,0.00000),V(108.99400,3.23500,0.00000),V(109.11600,3.13600,0.00000),V(109.21500,3.01400,0.00000),V(109.28900,2.87600,0.00000),V(109.33500,2.72600,0.00000),V(109.35000,2.57000,0.00000),V(109.33500,2.41400,0.00000),V(109.28900,2.26400,0.00000),V(109.21500,2.12600,0.00000),V(109.11600,2.00400,0.00000),V(108.99400,1.90500,0.00000),V(108.85600,1.83100,0.00000),V(108.70600,1.78500,0.00000)])]).extrude(V(0,0,0.01000)))
_s.append(Part.Face([_poly([V(111.24600,1.78500,0.00000),V(111.09000,1.77000,0.00000),V(110.93400,1.78500,0.00000),V(110.78400,1.83100,0.00000),V(110.64600,1.90500,0.00000),V(110.52400,2.00400,0.00000),V(110.42500,2.12600,0.00000),V(110.35100,2.26400,0.00000),V(110.30500,2.41400,0.00000),V(110.29000,2.57000,0.00000),V(110.30500,2.72600,0.00000),V(110.35100,2.87600,0.00000),V(110.42500,3.01400,0.00000),V(110.52400,3.13600,0.00000),V(110.64600,3.23500,0.00000),V(110.78400,3.30900,0.00000),V(110.93400,3.35500,0.00000),V(111.09000,3.37000,0.00000),V(111.24600,3.35500,0.00000),V(111.39600,3.30900,0.00000),V(111.53400,3.23500,0.00000),V(111.65600,3.13600,0.00000),V(111.75500,3.01400,0.00000),V(111.82900,2.87600,0.00000),V(111.87500,2.72600,0.00000),V(111.89000,2.57000,0.00000),V(111.87500,2.41400,0.00000),V(111.82900,2.26400,0.00000),V(111.75500,2.12600,0.00000),V(111.65600,2.00400,0.00000),V(111.53400,1.90500,0.00000),V(111.39600,1.83100,0.00000),V(111.24600,1.78500,0.00000)])]).extrude(V(0,0,0.01000)))
_s.append(Part.Face([_poly([V(113.93600,1.83100,0.00000),V(113.78600,1.78500,0.00000),V(113.63000,1.77000,0.00000),V(113.47400,1.78500,0.00000),V(113.32400,1.83100,0.00000),V(113.18600,1.90500,0.00000),V(113.06400,2.00400,0.00000),V(112.96500,2.12600,0.00000),V(112.89100,2.26400,0.00000),V(112.84500,2.41400,0.00000),V(112.83000,2.57000,0.00000),V(112.84500,2.72600,0.00000),V(112.89100,2.87600,0.00000),V(112.96500,3.01400,0.00000),V(113.06400,3.13600,0.00000),V(113.18600,3.23500,0.00000),V(113.32400,3.30900,0.00000),V(113.47400,3.35500,0.00000),V(113.63000,3.37000,0.00000),V(113.78600,3.35500,0.00000),V(113.93600,3.30900,0.00000),V(114.07400,3.23500,0.00000),V(114.19600,3.13600,0.00000),V(114.29500,3.01400,0.00000),V(114.36900,2.87600,0.00000),V(114.41500,2.72600,0.00000),V(114.43000,2.57000,0.00000),V(114.41500,2.41400,0.00000),V(114.36900,2.26400,0.00000),V(114.29500,2.12600,0.00000),V(114.19600,2.00400,0.00000),V(114.07400,1.90500,0.00000),V(113.93600,1.83100,0.00000)])]).extrude(V(0,0,0.01000)))
_s.append(Part.Face([_poly([V(116.32600,1.78500,0.00000),V(116.17000,1.77000,0.00000),V(116.01400,1.78500,0.00000),V(115.86400,1.83100,0.00000),V(115.72600,1.90500,0.00000),V(115.60400,2.00400,0.00000),V(115.50500,2.12600,0.00000),V(115.43100,2.26400,0.00000),V(115.38500,2.41400,0.00000),V(115.37000,2.57000,0.00000),V(115.38500,2.72600,0.00000),V(115.43100,2.87600,0.00000),V(115.50500,3.01400,0.00000),V(115.60400,3.13600,0.00000),V(115.72600,3.23500,0.00000),V(115.86400,3.30900,0.00000),V(116.01400,3.35500,0.00000),V(116.17000,3.37000,0.00000),V(116.32600,3.35500,0.00000),V(116.47600,3.30900,0.00000),V(116.61400,3.23500,0.00000),V(116.73600,3.13600,0.00000),V(116.83500,3.01400,0.00000),V(116.90900,2.87600,0.00000),V(116.95500,2.72600,0.00000),V(116.97000,2.57000,0.00000),V(116.95500,2.41400,0.00000),V(116.90900,2.26400,0.00000),V(116.83500,2.12600,0.00000),V(116.73600,2.00400,0.00000),V(116.61400,1.90500,0.00000),V(116.47600,1.83100,0.00000),V(116.32600,1.78500,0.00000)])]).extrude(V(0,0,0.01000)))
_s.append(Part.Face([_poly([V(118.86600,1.78500,0.00000),V(118.71000,1.77000,0.00000),V(118.55400,1.78500,0.00000),V(118.40400,1.83100,0.00000),V(118.26600,1.90500,0.00000),V(118.14400,2.00400,0.00000),V(118.04500,2.12600,0.00000),V(117.97100,2.26400,0.00000),V(117.92500,2.41400,0.00000),V(117.91000,2.57000,0.00000),V(117.92500,2.72600,0.00000),V(117.97100,2.87600,0.00000),V(118.04500,3.01400,0.00000),V(118.14400,3.13600,0.00000),V(118.26600,3.23500,0.00000),V(118.40400,3.30900,0.00000),V(118.55400,3.35500,0.00000),V(118.71000,3.37000,0.00000),V(118.86600,3.35500,0.00000),V(119.01600,3.30900,0.00000),V(119.15400,3.23500,0.00000),V(119.27600,3.13600,0.00000),V(119.37500,3.01400,0.00000),V(119.44900,2.87600,0.00000),V(119.49500,2.72600,0.00000),V(119.51000,2.57000,0.00000),V(119.49500,2.41400,0.00000),V(119.44900,2.26400,0.00000),V(119.37500,2.12600,0.00000),V(119.27600,2.00400,0.00000),V(119.15400,1.90500,0.00000),V(119.01600,1.83100,0.00000),V(118.86600,1.78500,0.00000)])]).extrude(V(0,0,0.01000)))
_s.append(Part.Face([_poly([V(121.55600,1.83100,0.00000),V(121.40600,1.78500,0.00000),V(121.25000,1.77000,0.00000),V(121.09400,1.78500,0.00000),V(120.94400,1.83100,0.00000),V(120.80600,1.90500,0.00000),V(120.68400,2.00400,0.00000),V(120.58500,2.12600,0.00000),V(120.51100,2.26400,0.00000),V(120.46500,2.41400,0.00000),V(120.45000,2.57000,0.00000),V(120.46500,2.72600,0.00000),V(120.51100,2.87600,0.00000),V(120.58500,3.01400,0.00000),V(120.68400,3.13600,0.00000),V(120.80600,3.23500,0.00000),V(120.94400,3.30900,0.00000),V(121.09400,3.35500,0.00000),V(121.25000,3.37000,0.00000),V(121.40600,3.35500,0.00000),V(121.55600,3.30900,0.00000),V(121.69400,3.23500,0.00000),V(121.81600,3.13600,0.00000),V(121.91500,3.01400,0.00000),V(121.98900,2.87600,0.00000),V(122.03500,2.72600,0.00000),V(122.05000,2.57000,0.00000),V(122.03500,2.41400,0.00000),V(121.98900,2.26400,0.00000),V(121.91500,2.12600,0.00000),V(121.81600,2.00400,0.00000),V(121.69400,1.90500,0.00000),V(121.55600,1.83100,0.00000)])]).extrude(V(0,0,0.01000)))
_s.append(Part.Face([_poly([V(124.09600,1.83100,0.00000),V(123.94600,1.78500,0.00000),V(123.79000,1.77000,0.00000),V(123.63400,1.78500,0.00000),V(123.48400,1.83100,0.00000),V(123.34600,1.90500,0.00000),V(123.22400,2.00400,0.00000),V(123.12500,2.12600,0.00000),V(123.05100,2.26400,0.00000),V(123.00500,2.41400,0.00000),V(122.99000,2.57000,0.00000),V(123.00500,2.72600,0.00000),V(123.05100,2.87600,0.00000),V(123.12500,3.01400,0.00000),V(123.22400,3.13600,0.00000),V(123.34600,3.23500,0.00000),V(123.48400,3.30900,0.00000),V(123.63400,3.35500,0.00000),V(123.79000,3.37000,0.00000),V(123.94600,3.35500,0.00000),V(124.09600,3.30900,0.00000),V(124.23400,3.23500,0.00000),V(124.35600,3.13600,0.00000),V(124.45500,3.01400,0.00000),V(124.52900,2.87600,0.00000),V(124.57500,2.72600,0.00000),V(124.59000,2.57000,0.00000),V(124.57500,2.41400,0.00000),V(124.52900,2.26400,0.00000),V(124.45500,2.12600,0.00000),V(124.35600,2.00400,0.00000),V(124.23400,1.90500,0.00000),V(124.09600,1.83100,0.00000)])]).extrude(V(0,0,0.01000)))
_s.append(Part.Face([_poly([V(126.63600,1.83100,0.00000),V(126.48600,1.78500,0.00000),V(126.33000,1.77000,0.00000),V(126.17400,1.78500,0.00000),V(126.02400,1.83100,0.00000),V(125.88600,1.90500,0.00000),V(125.76400,2.00400,0.00000),V(125.66500,2.12600,0.00000),V(125.59100,2.26400,0.00000),V(125.54500,2.41400,0.00000),V(125.53000,2.57000,0.00000),V(125.54500,2.72600,0.00000),V(125.59100,2.87600,0.00000),V(125.66500,3.01400,0.00000),V(125.76400,3.13600,0.00000),V(125.88600,3.23500,0.00000),V(126.02400,3.30900,0.00000),V(126.17400,3.35500,0.00000),V(126.33000,3.37000,0.00000),V(126.48600,3.35500,0.00000),V(126.63600,3.30900,0.00000),V(126.77400,3.23500,0.00000),V(126.89600,3.13600,0.00000),V(126.99500,3.01400,0.00000),V(127.06900,2.87600,0.00000),V(127.11500,2.72600,0.00000),V(127.13000,2.57000,0.00000),V(127.11500,2.41400,0.00000),V(127.06900,2.26400,0.00000),V(126.99500,2.12600,0.00000),V(126.89600,2.00400,0.00000),V(126.77400,1.90500,0.00000),V(126.63600,1.83100,0.00000)])]).extrude(V(0,0,0.01000)))
_s.append(Part.Face([_poly([V(129.02600,1.78500,0.00000),V(128.87000,1.77000,0.00000),V(128.71400,1.78500,0.00000),V(128.56400,1.83100,0.00000),V(128.42600,1.90500,0.00000),V(128.30400,2.00400,0.00000),V(128.20500,2.12600,0.00000),V(128.13100,2.26400,0.00000),V(128.08500,2.41400,0.00000),V(128.07000,2.57000,0.00000),V(128.08500,2.72600,0.00000),V(128.13100,2.87600,0.00000),V(128.20500,3.01400,0.00000),V(128.30400,3.13600,0.00000),V(128.42600,3.23500,0.00000),V(128.56400,3.30900,0.00000),V(128.71400,3.35500,0.00000),V(128.87000,3.37000,0.00000),V(129.02600,3.35500,0.00000),V(129.17600,3.30900,0.00000),V(129.31400,3.23500,0.00000),V(129.43600,3.13600,0.00000),V(129.53500,3.01400,0.00000),V(129.60900,2.87600,0.00000),V(129.65500,2.72600,0.00000),V(129.67000,2.57000,0.00000),V(129.65500,2.41400,0.00000),V(129.60900,2.26400,0.00000),V(129.53500,2.12600,0.00000),V(129.43600,2.00400,0.00000),V(129.31400,1.90500,0.00000),V(129.17600,1.83100,0.00000),V(129.02600,1.78500,0.00000)])]).extrude(V(0,0,0.01000)))
_s.append(Part.Face([_poly([V(131.56600,1.78500,0.00000),V(131.41000,1.77000,0.00000),V(131.25400,1.78500,0.00000),V(131.10400,1.83100,0.00000),V(130.96600,1.90500,0.00000),V(130.84400,2.00400,0.00000),V(130.74500,2.12600,0.00000),V(130.67100,2.26400,0.00000),V(130.62500,2.41400,0.00000),V(130.61000,2.57000,0.00000),V(130.62500,2.72600,0.00000),V(130.67100,2.87600,0.00000),V(130.74500,3.01400,0.00000),V(130.84400,3.13600,0.00000),V(130.96600,3.23500,0.00000),V(131.10400,3.30900,0.00000),V(131.25400,3.35500,0.00000),V(131.41000,3.37000,0.00000),V(131.56600,3.35500,0.00000),V(131.71600,3.30900,0.00000),V(131.85400,3.23500,0.00000),V(131.97600,3.13600,0.00000),V(132.07500,3.01400,0.00000),V(132.14900,2.87600,0.00000),V(132.19500,2.72600,0.00000),V(132.21000,2.57000,0.00000),V(132.19500,2.41400,0.00000),V(132.14900,2.26400,0.00000),V(132.07500,2.12600,0.00000),V(131.97600,2.00400,0.00000),V(131.85400,1.90500,0.00000),V(131.71600,1.83100,0.00000),V(131.56600,1.78500,0.00000)])]).extrude(V(0,0,0.01000)))
_s.append(Part.Face([_poly([V(134.25600,1.83100,0.00000),V(134.10600,1.78500,0.00000),V(133.95000,1.77000,0.00000),V(133.79400,1.78500,0.00000),V(133.64400,1.83100,0.00000),V(133.50600,1.90500,0.00000),V(133.38400,2.00400,0.00000),V(133.28500,2.12600,0.00000),V(133.21100,2.26400,0.00000),V(133.16500,2.41400,0.00000),V(133.15000,2.57000,0.00000),V(133.16500,2.72600,0.00000),V(133.21100,2.87600,0.00000),V(133.28500,3.01400,0.00000),V(133.38400,3.13600,0.00000),V(133.50600,3.23500,0.00000),V(133.64400,3.30900,0.00000),V(133.79400,3.35500,0.00000),V(133.95000,3.37000,0.00000),V(134.10600,3.35500,0.00000),V(134.25600,3.30900,0.00000),V(134.39400,3.23500,0.00000),V(134.51600,3.13600,0.00000),V(134.61500,3.01400,0.00000),V(134.68900,2.87600,0.00000),V(134.73500,2.72600,0.00000),V(134.75000,2.57000,0.00000),V(134.73500,2.41400,0.00000),V(134.68900,2.26400,0.00000),V(134.61500,2.12600,0.00000),V(134.51600,2.00400,0.00000),V(134.39400,1.90500,0.00000),V(134.25600,1.83100,0.00000)])]).extrude(V(0,0,0.01000)))
_s.append(Part.Face([_poly([V(136.64600,1.78500,0.00000),V(136.49000,1.77000,0.00000),V(136.33400,1.78500,0.00000),V(136.18400,1.83100,0.00000),V(136.04600,1.90500,0.00000),V(135.92400,2.00400,0.00000),V(135.82500,2.12600,0.00000),V(135.75100,2.26400,0.00000),V(135.70500,2.41400,0.00000),V(135.69000,2.57000,0.00000),V(135.70500,2.72600,0.00000),V(135.75100,2.87600,0.00000),V(135.82500,3.01400,0.00000),V(135.92400,3.13600,0.00000),V(136.04600,3.23500,0.00000),V(136.18400,3.30900,0.00000),V(136.33400,3.35500,0.00000),V(136.49000,3.37000,0.00000),V(136.64600,3.35500,0.00000),V(136.79600,3.30900,0.00000),V(136.93400,3.23500,0.00000),V(137.05600,3.13600,0.00000),V(137.15500,3.01400,0.00000),V(137.22900,2.87600,0.00000),V(137.27500,2.72600,0.00000),V(137.29000,2.57000,0.00000),V(137.27500,2.41400,0.00000),V(137.22900,2.26400,0.00000),V(137.15500,2.12600,0.00000),V(137.05600,2.00400,0.00000),V(136.93400,1.90500,0.00000),V(136.79600,1.83100,0.00000),V(136.64600,1.78500,0.00000)])]).extrude(V(0,0,0.01000)))
_s.append(Part.Face([_poly([V(139.18600,1.78500,0.00000),V(139.03000,1.77000,0.00000),V(138.87400,1.78500,0.00000),V(138.72400,1.83100,0.00000),V(138.58600,1.90500,0.00000),V(138.46400,2.00400,0.00000),V(138.36500,2.12600,0.00000),V(138.29100,2.26400,0.00000),V(138.24500,2.41400,0.00000),V(138.23000,2.57000,0.00000),V(138.24500,2.72600,0.00000),V(138.29100,2.87600,0.00000),V(138.36500,3.01400,0.00000),V(138.46400,3.13600,0.00000),V(138.58600,3.23500,0.00000),V(138.72400,3.30900,0.00000),V(138.87400,3.35500,0.00000),V(139.03000,3.37000,0.00000),V(139.18600,3.35500,0.00000),V(139.33600,3.30900,0.00000),V(139.47400,3.23500,0.00000),V(139.59600,3.13600,0.00000),V(139.69500,3.01400,0.00000),V(139.76900,2.87600,0.00000),V(139.81500,2.72600,0.00000),V(139.83000,2.57000,0.00000),V(139.81500,2.41400,0.00000),V(139.76900,2.26400,0.00000),V(139.69500,2.12600,0.00000),V(139.59600,2.00400,0.00000),V(139.47400,1.90500,0.00000),V(139.33600,1.83100,0.00000),V(139.18600,1.78500,0.00000)])]).extrude(V(0,0,0.01000)))
_s.append(Part.Face([_poly([V(103.77600,24.69100,0.00000),V(103.62600,24.64500,0.00000),V(103.47000,24.63000,0.00000),V(103.31400,24.64500,0.00000),V(103.16400,24.69100,0.00000),V(103.02600,24.76500,0.00000),V(102.90400,24.86400,0.00000),V(102.80500,24.98600,0.00000),V(102.73100,25.12400,0.00000),V(102.68500,25.27400,0.00000),V(102.67000,25.43000,0.00000),V(102.68500,25.58600,0.00000),V(102.73100,25.73600,0.00000),V(102.80500,25.87400,0.00000),V(102.90400,25.99600,0.00000),V(103.02600,26.09500,0.00000),V(103.16400,26.16900,0.00000),V(103.31400,26.21500,0.00000),V(103.47000,26.23000,0.00000),V(103.62600,26.21500,0.00000),V(103.77600,26.16900,0.00000),V(103.91400,26.09500,0.00000),V(104.03600,25.99600,0.00000),V(104.13500,25.87400,0.00000),V(104.20900,25.73600,0.00000),V(104.25500,25.58600,0.00000),V(104.27000,25.43000,0.00000),V(104.25500,25.27400,0.00000),V(104.20900,25.12400,0.00000),V(104.13500,24.98600,0.00000),V(104.03600,24.86400,0.00000),V(103.91400,24.76500,0.00000),V(103.77600,24.69100,0.00000)])]).extrude(V(0,0,0.01000)))
_s.append(Part.Face([_poly([V(106.16600,24.64500,0.00000),V(106.01000,24.63000,0.00000),V(105.85400,24.64500,0.00000),V(105.70400,24.69100,0.00000),V(105.56600,24.76500,0.00000),V(105.44400,24.86400,0.00000),V(105.34500,24.98600,0.00000),V(105.27100,25.12400,0.00000),V(105.22500,25.27400,0.00000),V(105.21000,25.43000,0.00000),V(105.22500,25.58600,0.00000),V(105.27100,25.73600,0.00000),V(105.34500,25.87400,0.00000),V(105.44400,25.99600,0.00000),V(105.56600,26.09500,0.00000),V(105.70400,26.16900,0.00000),V(105.85400,26.21500,0.00000),V(106.01000,26.23000,0.00000),V(106.16600,26.21500,0.00000),V(106.31600,26.16900,0.00000),V(106.45400,26.09500,0.00000),V(106.57600,25.99600,0.00000),V(106.67500,25.87400,0.00000),V(106.74900,25.73600,0.00000),V(106.79500,25.58600,0.00000),V(106.81000,25.43000,0.00000),V(106.79500,25.27400,0.00000),V(106.74900,25.12400,0.00000),V(106.67500,24.98600,0.00000),V(106.57600,24.86400,0.00000),V(106.45400,24.76500,0.00000),V(106.31600,24.69100,0.00000),V(106.16600,24.64500,0.00000)])]).extrude(V(0,0,0.01000)))
_s.append(Part.Face([_poly([V(108.70600,24.64500,0.00000),V(108.55000,24.63000,0.00000),V(108.39400,24.64500,0.00000),V(108.24400,24.69100,0.00000),V(108.10600,24.76500,0.00000),V(107.98400,24.86400,0.00000),V(107.88500,24.98600,0.00000),V(107.81100,25.12400,0.00000),V(107.76500,25.27400,0.00000),V(107.75000,25.43000,0.00000),V(107.76500,25.58600,0.00000),V(107.81100,25.73600,0.00000),V(107.88500,25.87400,0.00000),V(107.98400,25.99600,0.00000),V(108.10600,26.09500,0.00000),V(108.24400,26.16900,0.00000),V(108.39400,26.21500,0.00000),V(108.55000,26.23000,0.00000),V(108.70600,26.21500,0.00000),V(108.85600,26.16900,0.00000),V(108.99400,26.09500,0.00000),V(109.11600,25.99600,0.00000),V(109.21500,25.87400,0.00000),V(109.28900,25.73600,0.00000),V(109.33500,25.58600,0.00000),V(109.35000,25.43000,0.00000),V(109.33500,25.27400,0.00000),V(109.28900,25.12400,0.00000),V(109.21500,24.98600,0.00000),V(109.11600,24.86400,0.00000),V(108.99400,24.76500,0.00000),V(108.85600,24.69100,0.00000),V(108.70600,24.64500,0.00000)])]).extrude(V(0,0,0.01000)))
_s.append(Part.Face([_poly([V(111.39600,24.69100,0.00000),V(111.24600,24.64500,0.00000),V(111.09000,24.63000,0.00000),V(110.93400,24.64500,0.00000),V(110.78400,24.69100,0.00000),V(110.64600,24.76500,0.00000),V(110.52400,24.86400,0.00000),V(110.42500,24.98600,0.00000),V(110.35100,25.12400,0.00000),V(110.30500,25.27400,0.00000),V(110.29000,25.43000,0.00000),V(110.30500,25.58600,0.00000),V(110.35100,25.73600,0.00000),V(110.42500,25.87400,0.00000),V(110.52400,25.99600,0.00000),V(110.64600,26.09500,0.00000),V(110.78400,26.16900,0.00000),V(110.93400,26.21500,0.00000),V(111.09000,26.23000,0.00000),V(111.24600,26.21500,0.00000),V(111.39600,26.16900,0.00000),V(111.53400,26.09500,0.00000),V(111.65600,25.99600,0.00000),V(111.75500,25.87400,0.00000),V(111.82900,25.73600,0.00000),V(111.87500,25.58600,0.00000),V(111.89000,25.43000,0.00000),V(111.87500,25.27400,0.00000),V(111.82900,25.12400,0.00000),V(111.75500,24.98600,0.00000),V(111.65600,24.86400,0.00000),V(111.53400,24.76500,0.00000),V(111.39600,24.69100,0.00000)])]).extrude(V(0,0,0.01000)))
_s.append(Part.Face([_poly([V(113.78600,24.64500,0.00000),V(113.63000,24.63000,0.00000),V(113.47400,24.64500,0.00000),V(113.32400,24.69100,0.00000),V(113.18600,24.76500,0.00000),V(113.06400,24.86400,0.00000),V(112.96500,24.98600,0.00000),V(112.89100,25.12400,0.00000),V(112.84500,25.27400,0.00000),V(112.83000,25.43000,0.00000),V(112.84500,25.58600,0.00000),V(112.89100,25.73600,0.00000),V(112.96500,25.87400,0.00000),V(113.06400,25.99600,0.00000),V(113.18600,26.09500,0.00000),V(113.32400,26.16900,0.00000),V(113.47400,26.21500,0.00000),V(113.63000,26.23000,0.00000),V(113.78600,26.21500,0.00000),V(113.93600,26.16900,0.00000),V(114.07400,26.09500,0.00000),V(114.19600,25.99600,0.00000),V(114.29500,25.87400,0.00000),V(114.36900,25.73600,0.00000),V(114.41500,25.58600,0.00000),V(114.43000,25.43000,0.00000),V(114.41500,25.27400,0.00000),V(114.36900,25.12400,0.00000),V(114.29500,24.98600,0.00000),V(114.19600,24.86400,0.00000),V(114.07400,24.76500,0.00000),V(113.93600,24.69100,0.00000),V(113.78600,24.64500,0.00000)])]).extrude(V(0,0,0.01000)))
_s.append(Part.Face([_poly([V(116.32600,24.64500,0.00000),V(116.17000,24.63000,0.00000),V(116.01400,24.64500,0.00000),V(115.86400,24.69100,0.00000),V(115.72600,24.76500,0.00000),V(115.60400,24.86400,0.00000),V(115.50500,24.98600,0.00000),V(115.43100,25.12400,0.00000),V(115.38500,25.27400,0.00000),V(115.37000,25.43000,0.00000),V(115.38500,25.58600,0.00000),V(115.43100,25.73600,0.00000),V(115.50500,25.87400,0.00000),V(115.60400,25.99600,0.00000),V(115.72600,26.09500,0.00000),V(115.86400,26.16900,0.00000),V(116.01400,26.21500,0.00000),V(116.17000,26.23000,0.00000),V(116.32600,26.21500,0.00000),V(116.47600,26.16900,0.00000),V(116.61400,26.09500,0.00000),V(116.73600,25.99600,0.00000),V(116.83500,25.87400,0.00000),V(116.90900,25.73600,0.00000),V(116.95500,25.58600,0.00000),V(116.97000,25.43000,0.00000),V(116.95500,25.27400,0.00000),V(116.90900,25.12400,0.00000),V(116.83500,24.98600,0.00000),V(116.73600,24.86400,0.00000),V(116.61400,24.76500,0.00000),V(116.47600,24.69100,0.00000),V(116.32600,24.64500,0.00000)])]).extrude(V(0,0,0.01000)))
_s.append(Part.Face([_poly([V(119.01600,24.69100,0.00000),V(118.86600,24.64500,0.00000),V(118.71000,24.63000,0.00000),V(118.55400,24.64500,0.00000),V(118.40400,24.69100,0.00000),V(118.26600,24.76500,0.00000),V(118.14400,24.86400,0.00000),V(118.04500,24.98600,0.00000),V(117.97100,25.12400,0.00000),V(117.92500,25.27400,0.00000),V(117.91000,25.43000,0.00000),V(117.92500,25.58600,0.00000),V(117.97100,25.73600,0.00000),V(118.04500,25.87400,0.00000),V(118.14400,25.99600,0.00000),V(118.26600,26.09500,0.00000),V(118.40400,26.16900,0.00000),V(118.55400,26.21500,0.00000),V(118.71000,26.23000,0.00000),V(118.86600,26.21500,0.00000),V(119.01600,26.16900,0.00000),V(119.15400,26.09500,0.00000),V(119.27600,25.99600,0.00000),V(119.37500,25.87400,0.00000),V(119.44900,25.73600,0.00000),V(119.49500,25.58600,0.00000),V(119.51000,25.43000,0.00000),V(119.49500,25.27400,0.00000),V(119.44900,25.12400,0.00000),V(119.37500,24.98600,0.00000),V(119.27600,24.86400,0.00000),V(119.15400,24.76500,0.00000),V(119.01600,24.69100,0.00000)])]).extrude(V(0,0,0.01000)))
_s.append(Part.Face([_poly([V(121.40600,24.64500,0.00000),V(121.25000,24.63000,0.00000),V(121.09400,24.64500,0.00000),V(120.94400,24.69100,0.00000),V(120.80600,24.76500,0.00000),V(120.68400,24.86400,0.00000),V(120.58500,24.98600,0.00000),V(120.51100,25.12400,0.00000),V(120.46500,25.27400,0.00000),V(120.45000,25.43000,0.00000),V(120.46500,25.58600,0.00000),V(120.51100,25.73600,0.00000),V(120.58500,25.87400,0.00000),V(120.68400,25.99600,0.00000),V(120.80600,26.09500,0.00000),V(120.94400,26.16900,0.00000),V(121.09400,26.21500,0.00000),V(121.25000,26.23000,0.00000),V(121.40600,26.21500,0.00000),V(121.55600,26.16900,0.00000),V(121.69400,26.09500,0.00000),V(121.81600,25.99600,0.00000),V(121.91500,25.87400,0.00000),V(121.98900,25.73600,0.00000),V(122.03500,25.58600,0.00000),V(122.05000,25.43000,0.00000),V(122.03500,25.27400,0.00000),V(121.98900,25.12400,0.00000),V(121.91500,24.98600,0.00000),V(121.81600,24.86400,0.00000),V(121.69400,24.76500,0.00000),V(121.55600,24.69100,0.00000),V(121.40600,24.64500,0.00000)])]).extrude(V(0,0,0.01000)))
_s.append(Part.Face([_poly([V(123.94600,24.64500,0.00000),V(123.79000,24.63000,0.00000),V(123.63400,24.64500,0.00000),V(123.48400,24.69100,0.00000),V(123.34600,24.76500,0.00000),V(123.22400,24.86400,0.00000),V(123.12500,24.98600,0.00000),V(123.05100,25.12400,0.00000),V(123.00500,25.27400,0.00000),V(122.99000,25.43000,0.00000),V(123.00500,25.58600,0.00000),V(123.05100,25.73600,0.00000),V(123.12500,25.87400,0.00000),V(123.22400,25.99600,0.00000),V(123.34600,26.09500,0.00000),V(123.48400,26.16900,0.00000),V(123.63400,26.21500,0.00000),V(123.79000,26.23000,0.00000),V(123.94600,26.21500,0.00000),V(124.09600,26.16900,0.00000),V(124.23400,26.09500,0.00000),V(124.35600,25.99600,0.00000),V(124.45500,25.87400,0.00000),V(124.52900,25.73600,0.00000),V(124.57500,25.58600,0.00000),V(124.59000,25.43000,0.00000),V(124.57500,25.27400,0.00000),V(124.52900,25.12400,0.00000),V(124.45500,24.98600,0.00000),V(124.35600,24.86400,0.00000),V(124.23400,24.76500,0.00000),V(124.09600,24.69100,0.00000),V(123.94600,24.64500,0.00000)])]).extrude(V(0,0,0.01000)))
_s.append(Part.Face([_poly([V(126.63600,24.69100,0.00000),V(126.48600,24.64500,0.00000),V(126.33000,24.63000,0.00000),V(126.17400,24.64500,0.00000),V(126.02400,24.69100,0.00000),V(125.88600,24.76500,0.00000),V(125.76400,24.86400,0.00000),V(125.66500,24.98600,0.00000),V(125.59100,25.12400,0.00000),V(125.54500,25.27400,0.00000),V(125.53000,25.43000,0.00000),V(125.54500,25.58600,0.00000),V(125.59100,25.73600,0.00000),V(125.66500,25.87400,0.00000),V(125.76400,25.99600,0.00000),V(125.88600,26.09500,0.00000),V(126.02400,26.16900,0.00000),V(126.17400,26.21500,0.00000),V(126.33000,26.23000,0.00000),V(126.48600,26.21500,0.00000),V(126.63600,26.16900,0.00000),V(126.77400,26.09500,0.00000),V(126.89600,25.99600,0.00000),V(126.99500,25.87400,0.00000),V(127.06900,25.73600,0.00000),V(127.11500,25.58600,0.00000),V(127.13000,25.43000,0.00000),V(127.11500,25.27400,0.00000),V(127.06900,25.12400,0.00000),V(126.99500,24.98600,0.00000),V(126.89600,24.86400,0.00000),V(126.77400,24.76500,0.00000),V(126.63600,24.69100,0.00000)])]).extrude(V(0,0,0.01000)))
_s.append(Part.Face([_poly([V(129.02600,24.64500,0.00000),V(128.87000,24.63000,0.00000),V(128.71400,24.64500,0.00000),V(128.56400,24.69100,0.00000),V(128.42600,24.76500,0.00000),V(128.30400,24.86400,0.00000),V(128.20500,24.98600,0.00000),V(128.13100,25.12400,0.00000),V(128.08500,25.27400,0.00000),V(128.07000,25.43000,0.00000),V(128.08500,25.58600,0.00000),V(128.13100,25.73600,0.00000),V(128.20500,25.87400,0.00000),V(128.30400,25.99600,0.00000),V(128.42600,26.09500,0.00000),V(128.56400,26.16900,0.00000),V(128.71400,26.21500,0.00000),V(128.87000,26.23000,0.00000),V(129.02600,26.21500,0.00000),V(129.17600,26.16900,0.00000),V(129.31400,26.09500,0.00000),V(129.43600,25.99600,0.00000),V(129.53500,25.87400,0.00000),V(129.60900,25.73600,0.00000),V(129.65500,25.58600,0.00000),V(129.67000,25.43000,0.00000),V(129.65500,25.27400,0.00000),V(129.60900,25.12400,0.00000),V(129.53500,24.98600,0.00000),V(129.43600,24.86400,0.00000),V(129.31400,24.76500,0.00000),V(129.17600,24.69100,0.00000),V(129.02600,24.64500,0.00000)])]).extrude(V(0,0,0.01000)))
_s.append(Part.Face([_poly([V(131.56600,24.64500,0.00000),V(131.41000,24.63000,0.00000),V(131.25400,24.64500,0.00000),V(131.10400,24.69100,0.00000),V(130.96600,24.76500,0.00000),V(130.84400,24.86400,0.00000),V(130.74500,24.98600,0.00000),V(130.67100,25.12400,0.00000),V(130.62500,25.27400,0.00000),V(130.61000,25.43000,0.00000),V(130.62500,25.58600,0.00000),V(130.67100,25.73600,0.00000),V(130.74500,25.87400,0.00000),V(130.84400,25.99600,0.00000),V(130.96600,26.09500,0.00000),V(131.10400,26.16900,0.00000),V(131.25400,26.21500,0.00000),V(131.41000,26.23000,0.00000),V(131.56600,26.21500,0.00000),V(131.71600,26.16900,0.00000),V(131.85400,26.09500,0.00000),V(131.97600,25.99600,0.00000),V(132.07500,25.87400,0.00000),V(132.14900,25.73600,0.00000),V(132.19500,25.58600,0.00000),V(132.21000,25.43000,0.00000),V(132.19500,25.27400,0.00000),V(132.14900,25.12400,0.00000),V(132.07500,24.98600,0.00000),V(131.97600,24.86400,0.00000),V(131.85400,24.76500,0.00000),V(131.71600,24.69100,0.00000),V(131.56600,24.64500,0.00000)])]).extrude(V(0,0,0.01000)))
_s.append(Part.Face([_poly([V(134.25600,24.69100,0.00000),V(134.10600,24.64500,0.00000),V(133.95000,24.63000,0.00000),V(133.79400,24.64500,0.00000),V(133.64400,24.69100,0.00000),V(133.50600,24.76500,0.00000),V(133.38400,24.86400,0.00000),V(133.28500,24.98600,0.00000),V(133.21100,25.12400,0.00000),V(133.16500,25.27400,0.00000),V(133.15000,25.43000,0.00000),V(133.16500,25.58600,0.00000),V(133.21100,25.73600,0.00000),V(133.28500,25.87400,0.00000),V(133.38400,25.99600,0.00000),V(133.50600,26.09500,0.00000),V(133.64400,26.16900,0.00000),V(133.79400,26.21500,0.00000),V(133.95000,26.23000,0.00000),V(134.10600,26.21500,0.00000),V(134.25600,26.16900,0.00000),V(134.39400,26.09500,0.00000),V(134.51600,25.99600,0.00000),V(134.61500,25.87400,0.00000),V(134.68900,25.73600,0.00000),V(134.73500,25.58600,0.00000),V(134.75000,25.43000,0.00000),V(134.73500,25.27400,0.00000),V(134.68900,25.12400,0.00000),V(134.61500,24.98600,0.00000),V(134.51600,24.86400,0.00000),V(134.39400,24.76500,0.00000),V(134.25600,24.69100,0.00000)])]).extrude(V(0,0,0.01000)))
_s.append(Part.Face([_poly([V(136.64600,24.64500,0.00000),V(136.49000,24.63000,0.00000),V(136.33400,24.64500,0.00000),V(136.18400,24.69100,0.00000),V(136.04600,24.76500,0.00000),V(135.92400,24.86400,0.00000),V(135.82500,24.98600,0.00000),V(135.75100,25.12400,0.00000),V(135.70500,25.27400,0.00000),V(135.69000,25.43000,0.00000),V(135.70500,25.58600,0.00000),V(135.75100,25.73600,0.00000),V(135.82500,25.87400,0.00000),V(135.92400,25.99600,0.00000),V(136.04600,26.09500,0.00000),V(136.18400,26.16900,0.00000),V(136.33400,26.21500,0.00000),V(136.49000,26.23000,0.00000),V(136.64600,26.21500,0.00000),V(136.79600,26.16900,0.00000),V(136.93400,26.09500,0.00000),V(137.05600,25.99600,0.00000),V(137.15500,25.87400,0.00000),V(137.22900,25.73600,0.00000),V(137.27500,25.58600,0.00000),V(137.29000,25.43000,0.00000),V(137.27500,25.27400,0.00000),V(137.22900,25.12400,0.00000),V(137.15500,24.98600,0.00000),V(137.05600,24.86400,0.00000),V(136.93400,24.76500,0.00000),V(136.79600,24.69100,0.00000),V(136.64600,24.64500,0.00000)])]).extrude(V(0,0,0.01000)))
_s.append(Part.Face([_poly([V(139.18600,24.64500,0.00000),V(139.03000,24.63000,0.00000),V(138.87400,24.64500,0.00000),V(138.72400,24.69100,0.00000),V(138.58600,24.76500,0.00000),V(138.46400,24.86400,0.00000),V(138.36500,24.98600,0.00000),V(138.29100,25.12400,0.00000),V(138.24500,25.27400,0.00000),V(138.23000,25.43000,0.00000),V(138.24500,25.58600,0.00000),V(138.29100,25.73600,0.00000),V(138.36500,25.87400,0.00000),V(138.46400,25.99600,0.00000),V(138.58600,26.09500,0.00000),V(138.72400,26.16900,0.00000),V(138.87400,26.21500,0.00000),V(139.03000,26.23000,0.00000),V(139.18600,26.21500,0.00000),V(139.33600,26.16900,0.00000),V(139.47400,26.09500,0.00000),V(139.59600,25.99600,0.00000),V(139.69500,25.87400,0.00000),V(139.76900,25.73600,0.00000),V(139.81500,25.58600,0.00000),V(139.83000,25.43000,0.00000),V(139.81500,25.27400,0.00000),V(139.76900,25.12400,0.00000),V(139.69500,24.98600,0.00000),V(139.59600,24.86400,0.00000),V(139.47400,24.76500,0.00000),V(139.33600,24.69100,0.00000),V(139.18600,24.64500,0.00000)])]).extrude(V(0,0,0.01000)))
_add('L49' + '_L49', _fuse(_s), (0.2353,0.7059,0.2941), surface=True)
# --- layer 61 (L61) : z 0.0100..0.0200 mm ---
_s = []
_s.append(Part.Face([_poly([V(-0.05000,27.42071,0.01000),V(0.57929,28.05000,0.01000),V(28.82071,28.05000,0.01000),V(29.45000,27.42071,0.01000),V(29.45000,0.57929,0.01000),V(28.82071,-0.05000,0.01000),V(0.57929,-0.05000,0.01000),V(-0.05000,0.57929,0.01000),V(-0.05000,27.42071,0.01000)]), _poly([V(29.35000,0.62071,0.01000),V(29.35000,27.37929,0.01000),V(28.77929,27.95000,0.01000),V(0.62071,27.95000,0.01000),V(0.05000,27.37929,0.01000),V(0.05000,0.62071,0.01000),V(0.62071,0.05000,0.01000),V(28.77929,0.05000,0.01000),V(29.35000,0.62071,0.01000)])]).extrude(V(0,0,0.01000)))
_s.append(Part.Face([_poly([V(1.57929,27.05000,0.01000),V(27.82071,27.05000,0.01000),V(28.45000,26.42071,0.01000),V(28.45000,1.57929,0.01000),V(27.82071,0.95000,0.01000),V(1.57929,0.95000,0.01000),V(0.95000,1.57929,0.01000),V(0.95000,26.42071,0.01000),V(1.57929,27.05000,0.01000)]), _poly([V(28.35000,26.37929,0.01000),V(27.77929,26.95000,0.01000),V(1.62071,26.95000,0.01000),V(1.05000,26.37929,0.01000),V(1.05000,1.62071,0.01000),V(1.62071,1.05000,0.01000),V(27.77929,1.05000,0.01000),V(28.35000,1.62071,0.01000),V(28.35000,26.37929,0.01000)])]).extrude(V(0,0,0.01000)))
_s.append(Part.Face([_poly([V(37.97929,28.05000,0.01000),V(78.92071,28.05000,0.01000),V(79.55000,27.42071,0.01000),V(79.55000,0.57929,0.01000),V(78.92071,-0.05000,0.01000),V(37.97929,-0.05000,0.01000),V(37.35000,0.57929,0.01000),V(37.35000,27.42071,0.01000),V(37.97929,28.05000,0.01000)]), _poly([V(79.45000,27.37929,0.01000),V(78.87929,27.95000,0.01000),V(38.02071,27.95000,0.01000),V(37.45000,27.37929,0.01000),V(37.45000,0.62071,0.01000),V(38.02071,0.05000,0.01000),V(78.87929,0.05000,0.01000),V(79.45000,0.62071,0.01000),V(79.45000,27.37929,0.01000)])]).extrude(V(0,0,0.01000)))
_s.append(Part.Face([_poly([V(38.35000,26.42071,0.01000),V(38.97929,27.05000,0.01000),V(77.92071,27.05000,0.01000),V(78.55000,26.42071,0.01000),V(78.55000,1.57929,0.01000),V(77.92071,0.95000,0.01000),V(38.97929,0.95000,0.01000),V(38.35000,1.57929,0.01000),V(38.35000,26.42071,0.01000)]), _poly([V(78.45000,1.62071,0.01000),V(78.45000,26.37929,0.01000),V(77.87929,26.95000,0.01000),V(39.02071,26.95000,0.01000),V(38.45000,26.37929,0.01000),V(38.45000,1.62071,0.01000),V(39.02071,1.05000,0.01000),V(77.87929,1.05000,0.01000),V(78.45000,1.62071,0.01000)])]).extrude(V(0,0,0.01000)))
_s.append(Part.Face([_poly([V(88.07929,28.05000,0.01000),V(141.72071,28.05000,0.01000),V(142.35000,27.42071,0.01000),V(142.35000,0.57929,0.01000),V(141.72071,-0.05000,0.01000),V(88.07929,-0.05000,0.01000),V(87.45000,0.57929,0.01000),V(87.45000,27.42071,0.01000),V(88.07929,28.05000,0.01000)]), _poly([V(142.25000,27.37929,0.01000),V(141.67929,27.95000,0.01000),V(88.12071,27.95000,0.01000),V(87.55000,27.37929,0.01000),V(87.55000,0.62071,0.01000),V(88.12071,0.05000,0.01000),V(141.67929,0.05000,0.01000),V(142.25000,0.62071,0.01000),V(142.25000,27.37929,0.01000)])]).extrude(V(0,0,0.01000)))
_s.append(Part.Face([_poly([V(89.07929,27.05000,0.01000),V(140.72071,27.05000,0.01000),V(141.35000,26.42071,0.01000),V(141.35000,1.57929,0.01000),V(140.72071,0.95000,0.01000),V(89.07929,0.95000,0.01000),V(88.45000,1.57929,0.01000),V(88.45000,26.42071,0.01000),V(89.07929,27.05000,0.01000)]), _poly([V(141.25000,26.37929,0.01000),V(140.67929,26.95000,0.01000),V(89.12071,26.95000,0.01000),V(88.55000,26.37929,0.01000),V(88.55000,1.62071,0.01000),V(89.12071,1.05000,0.01000),V(140.67929,1.05000,0.01000),V(141.25000,1.62071,0.01000),V(141.25000,26.37929,0.01000)])]).extrude(V(0,0,0.01000)))
_add('L61' + '_L61', _fuse(_s), (1.0000,0.9804,0.7843), surface=True)
# --- layer 62 (L62) : z 0.0200..0.0300 mm ---
_s = []
_s.append(Part.Face([_poly([V(1.98000,2.52100,0.02000),V(1.96600,2.47400,0.02000),V(1.94300,2.43100,0.02000),V(1.91200,2.39300,0.02000),V(1.87400,2.36200,0.02000),V(1.83100,2.33900,0.02000),V(1.78400,2.32500,0.02000),V(1.73500,2.32000,0.02000),V(1.68600,2.32500,0.02000),V(1.63900,2.33900,0.02000),V(1.59600,2.36200,0.02000),V(1.55800,2.39300,0.02000),V(1.52700,2.43100,0.02000),V(1.50400,2.47400,0.02000),V(1.49000,2.52100,0.02000),V(1.48500,2.57000,0.02000),V(1.49000,2.61900,0.02000),V(1.50400,2.66600,0.02000),V(1.52700,2.70900,0.02000),V(1.55800,2.74700,0.02000),V(1.59600,2.77800,0.02000),V(1.63900,2.80100,0.02000),V(1.68600,2.81500,0.02000),V(1.73500,2.82000,0.02000),V(1.78400,2.81500,0.02000),V(1.83100,2.80100,0.02000),V(1.87400,2.77800,0.02000),V(1.91200,2.74700,0.02000),V(1.94300,2.70900,0.02000),V(1.96600,2.66600,0.02000),V(1.98000,2.61900,0.02000),V(1.98500,2.57000,0.02000),V(1.98000,2.52100,0.02000)])]).extrude(V(0,0,0.01000)))
_s.append(Part.Face([_poly([V(39.36600,2.47400,0.02000),V(39.34300,2.43100,0.02000),V(39.31200,2.39300,0.02000),V(39.27400,2.36200,0.02000),V(39.23100,2.33900,0.02000),V(39.18400,2.32500,0.02000),V(39.13500,2.32000,0.02000),V(39.08600,2.32500,0.02000),V(39.03900,2.33900,0.02000),V(38.99600,2.36200,0.02000),V(38.95800,2.39300,0.02000),V(38.92700,2.43100,0.02000),V(38.90400,2.47400,0.02000),V(38.89000,2.52100,0.02000),V(38.88500,2.57000,0.02000),V(38.89000,2.61900,0.02000),V(38.90400,2.66600,0.02000),V(38.92700,2.70900,0.02000),V(38.95800,2.74700,0.02000),V(38.99600,2.77800,0.02000),V(39.03900,2.80100,0.02000),V(39.08600,2.81500,0.02000),V(39.13500,2.82000,0.02000),V(39.18400,2.81500,0.02000),V(39.23100,2.80100,0.02000),V(39.27400,2.77800,0.02000),V(39.31200,2.74700,0.02000),V(39.34300,2.70900,0.02000),V(39.36600,2.66600,0.02000),V(39.38000,2.61900,0.02000),V(39.38500,2.57000,0.02000),V(39.38000,2.52100,0.02000),V(39.36600,2.47400,0.02000)])]).extrude(V(0,0,0.01000)))
_s.append(Part.Face([_poly([V(89.46600,2.47400,0.02000),V(89.44300,2.43100,0.02000),V(89.41200,2.39300,0.02000),V(89.37400,2.36200,0.02000),V(89.33100,2.33900,0.02000),V(89.28400,2.32500,0.02000),V(89.23500,2.32000,0.02000),V(89.18600,2.32500,0.02000),V(89.13900,2.33900,0.02000),V(89.09600,2.36200,0.02000),V(89.05800,2.39300,0.02000),V(89.02700,2.43100,0.02000),V(89.00400,2.47400,0.02000),V(88.99000,2.52100,0.02000),V(88.98500,2.57000,0.02000),V(88.99000,2.61900,0.02000),V(89.00400,2.66600,0.02000),V(89.02700,2.70900,0.02000),V(89.05800,2.74700,0.02000),V(89.09600,2.77800,0.02000),V(89.13900,2.80100,0.02000),V(89.18600,2.81500,0.02000),V(89.23500,2.82000,0.02000),V(89.28400,2.81500,0.02000),V(89.33100,2.80100,0.02000),V(89.37400,2.77800,0.02000),V(89.41200,2.74700,0.02000),V(89.44300,2.70900,0.02000),V(89.46600,2.66600,0.02000),V(89.48000,2.61900,0.02000),V(89.48500,2.57000,0.02000),V(89.48000,2.52100,0.02000),V(89.46600,2.47400,0.02000)])]).extrude(V(0,0,0.01000)))
_add('L62' + '_L62', _fuse(_s), (0.5020,0.0000,0.0000), surface=True)
# --- layer 63 (L63) : z 0.0300..0.0400 mm ---
_s = []
_s.append(Part.Face([_poly([V(3.42600,1.78500,0.03000),V(3.27000,1.77000,0.03000),V(3.11400,1.78500,0.03000),V(2.96400,1.83100,0.03000),V(2.82600,1.90500,0.03000),V(2.70400,2.00400,0.03000),V(2.60500,2.12600,0.03000),V(2.53100,2.26400,0.03000),V(2.48500,2.41400,0.03000),V(2.47000,2.57000,0.03000),V(2.48500,2.72600,0.03000),V(2.53100,2.87600,0.03000),V(2.60500,3.01400,0.03000),V(2.70400,3.13600,0.03000),V(2.82600,3.23500,0.03000),V(2.96400,3.30900,0.03000),V(3.11400,3.35500,0.03000),V(3.27000,3.37000,0.03000),V(3.42600,3.35500,0.03000),V(3.57600,3.30900,0.03000),V(3.71400,3.23500,0.03000),V(3.83600,3.13600,0.03000),V(3.93500,3.01400,0.03000),V(4.00900,2.87600,0.03000),V(4.05500,2.72600,0.03000),V(4.07000,2.57000,0.03000),V(4.05500,2.41400,0.03000),V(4.00900,2.26400,0.03000),V(3.93500,2.12600,0.03000),V(3.83600,2.00400,0.03000),V(3.71400,1.90500,0.03000),V(3.57600,1.83100,0.03000),V(3.42600,1.78500,0.03000)])]).extrude(V(0,0,0.01000)))
_s.append(Part.Face([_poly([V(13.58600,1.78500,0.03000),V(13.43000,1.77000,0.03000),V(13.27400,1.78500,0.03000),V(13.12400,1.83100,0.03000),V(12.98600,1.90500,0.03000),V(12.86400,2.00400,0.03000),V(12.76500,2.12600,0.03000),V(12.69100,2.26400,0.03000),V(12.64500,2.41400,0.03000),V(12.63000,2.57000,0.03000),V(12.64500,2.72600,0.03000),V(12.69100,2.87600,0.03000),V(12.76500,3.01400,0.03000),V(12.86400,3.13600,0.03000),V(12.98600,3.23500,0.03000),V(13.12400,3.30900,0.03000),V(13.27400,3.35500,0.03000),V(13.43000,3.37000,0.03000),V(13.58600,3.35500,0.03000),V(13.73600,3.30900,0.03000),V(13.87400,3.23500,0.03000),V(13.99600,3.13600,0.03000),V(14.09500,3.01400,0.03000),V(14.16900,2.87600,0.03000),V(14.21500,2.72600,0.03000),V(14.23000,2.57000,0.03000),V(14.21500,2.41400,0.03000),V(14.16900,2.26400,0.03000),V(14.09500,2.12600,0.03000),V(13.99600,2.00400,0.03000),V(13.87400,1.90500,0.03000),V(13.73600,1.83100,0.03000),V(13.58600,1.78500,0.03000)])]).extrude(V(0,0,0.01000)))
_s.append(Part.Face([_poly([V(5.81000,1.77000,0.03000),V(5.65400,1.78500,0.03000),V(5.50400,1.83100,0.03000),V(5.36600,1.90500,0.03000),V(5.24400,2.00400,0.03000),V(5.14500,2.12600,0.03000),V(5.07100,2.26400,0.03000),V(5.02500,2.41400,0.03000),V(5.01000,2.57000,0.03000),V(5.02500,2.72600,0.03000),V(5.07100,2.87600,0.03000),V(5.14500,3.01400,0.03000),V(5.24400,3.13600,0.03000),V(5.36600,3.23500,0.03000),V(5.50400,3.30900,0.03000),V(5.65400,3.35500,0.03000),V(5.81000,3.37000,0.03000),V(5.96600,3.35500,0.03000),V(6.11600,3.30900,0.03000),V(6.25400,3.23500,0.03000),V(6.37600,3.13600,0.03000),V(6.47500,3.01400,0.03000),V(6.54900,2.87600,0.03000),V(6.59500,2.72600,0.03000),V(6.61000,2.57000,0.03000),V(6.59500,2.41400,0.03000),V(6.54900,2.26400,0.03000),V(6.47500,2.12600,0.03000),V(6.37600,2.00400,0.03000),V(6.25400,1.90500,0.03000),V(6.11600,1.83100,0.03000),V(5.96600,1.78500,0.03000),V(5.81000,1.77000,0.03000)])]).extrude(V(0,0,0.01000)))
_s.append(Part.Face([_poly([V(10.89000,1.77000,0.03000),V(10.73400,1.78500,0.03000),V(10.58400,1.83100,0.03000),V(10.44600,1.90500,0.03000),V(10.32400,2.00400,0.03000),V(10.22500,2.12600,0.03000),V(10.15100,2.26400,0.03000),V(10.10500,2.41400,0.03000),V(10.09000,2.57000,0.03000),V(10.10500,2.72600,0.03000),V(10.15100,2.87600,0.03000),V(10.22500,3.01400,0.03000),V(10.32400,3.13600,0.03000),V(10.44600,3.23500,0.03000),V(10.58400,3.30900,0.03000),V(10.73400,3.35500,0.03000),V(10.89000,3.37000,0.03000),V(11.04600,3.35500,0.03000),V(11.19600,3.30900,0.03000),V(11.33400,3.23500,0.03000),V(11.45600,3.13600,0.03000),V(11.55500,3.01400,0.03000),V(11.62900,2.87600,0.03000),V(11.67500,2.72600,0.03000),V(11.69000,2.57000,0.03000),V(11.67500,2.41400,0.03000),V(11.62900,2.26400,0.03000),V(11.55500,2.12600,0.03000),V(11.45600,2.00400,0.03000),V(11.33400,1.90500,0.03000),V(11.19600,1.83100,0.03000),V(11.04600,1.78500,0.03000),V(10.89000,1.77000,0.03000)])]).extrude(V(0,0,0.01000)))
_s.append(Part.Face([_poly([V(8.50600,1.78500,0.03000),V(8.35000,1.77000,0.03000),V(8.19400,1.78500,0.03000),V(8.04400,1.83100,0.03000),V(7.90600,1.90500,0.03000),V(7.78400,2.00400,0.03000),V(7.68500,2.12600,0.03000),V(7.61100,2.26400,0.03000),V(7.56500,2.41400,0.03000),V(7.55000,2.57000,0.03000),V(7.56500,2.72600,0.03000),V(7.61100,2.87600,0.03000),V(7.68500,3.01400,0.03000),V(7.78400,3.13600,0.03000),V(7.90600,3.23500,0.03000),V(8.04400,3.30900,0.03000),V(8.19400,3.35500,0.03000),V(8.35000,3.37000,0.03000),V(8.50600,3.35500,0.03000),V(8.65600,3.30900,0.03000),V(8.79400,3.23500,0.03000),V(8.91600,3.13600,0.03000),V(9.01500,3.01400,0.03000),V(9.08900,2.87600,0.03000),V(9.13500,2.72600,0.03000),V(9.15000,2.57000,0.03000),V(9.13500,2.41400,0.03000),V(9.08900,2.26400,0.03000),V(9.01500,2.12600,0.03000),V(8.91600,2.00400,0.03000),V(8.79400,1.90500,0.03000),V(8.65600,1.83100,0.03000),V(8.50600,1.78500,0.03000)])]).extrude(V(0,0,0.01000)))
_s.append(Part.Face([_poly([V(15.97000,1.77000,0.03000),V(15.81400,1.78500,0.03000),V(15.66400,1.83100,0.03000),V(15.52600,1.90500,0.03000),V(15.40400,2.00400,0.03000),V(15.30500,2.12600,0.03000),V(15.23100,2.26400,0.03000),V(15.18500,2.41400,0.03000),V(15.17000,2.57000,0.03000),V(15.18500,2.72600,0.03000),V(15.23100,2.87600,0.03000),V(15.30500,3.01400,0.03000),V(15.40400,3.13600,0.03000),V(15.52600,3.23500,0.03000),V(15.66400,3.30900,0.03000),V(15.81400,3.35500,0.03000),V(15.97000,3.37000,0.03000),V(16.12600,3.35500,0.03000),V(16.27600,3.30900,0.03000),V(16.41400,3.23500,0.03000),V(16.53600,3.13600,0.03000),V(16.63500,3.01400,0.03000),V(16.70900,2.87600,0.03000),V(16.75500,2.72600,0.03000),V(16.77000,2.57000,0.03000),V(16.75500,2.41400,0.03000),V(16.70900,2.26400,0.03000),V(16.63500,2.12600,0.03000),V(16.53600,2.00400,0.03000),V(16.41400,1.90500,0.03000),V(16.27600,1.83100,0.03000),V(16.12600,1.78500,0.03000),V(15.97000,1.77000,0.03000)])]).extrude(V(0,0,0.01000)))
_s.append(Part.Face([_poly([V(18.66600,1.78500,0.03000),V(18.51000,1.77000,0.03000),V(18.35400,1.78500,0.03000),V(18.20400,1.83100,0.03000),V(18.06600,1.90500,0.03000),V(17.94400,2.00400,0.03000),V(17.84500,2.12600,0.03000),V(17.77100,2.26400,0.03000),V(17.72500,2.41400,0.03000),V(17.71000,2.57000,0.03000),V(17.72500,2.72600,0.03000),V(17.77100,2.87600,0.03000),V(17.84500,3.01400,0.03000),V(17.94400,3.13600,0.03000),V(18.06600,3.23500,0.03000),V(18.20400,3.30900,0.03000),V(18.35400,3.35500,0.03000),V(18.51000,3.37000,0.03000),V(18.66600,3.35500,0.03000),V(18.81600,3.30900,0.03000),V(18.95400,3.23500,0.03000),V(19.07600,3.13600,0.03000),V(19.17500,3.01400,0.03000),V(19.24900,2.87600,0.03000),V(19.29500,2.72600,0.03000),V(19.31000,2.57000,0.03000),V(19.29500,2.41400,0.03000),V(19.24900,2.26400,0.03000),V(19.17500,2.12600,0.03000),V(19.07600,2.00400,0.03000),V(18.95400,1.90500,0.03000),V(18.81600,1.83100,0.03000),V(18.66600,1.78500,0.03000)])]).extrude(V(0,0,0.01000)))
_s.append(Part.Face([_poly([V(21.05000,1.77000,0.03000),V(20.89400,1.78500,0.03000),V(20.74400,1.83100,0.03000),V(20.60600,1.90500,0.03000),V(20.48400,2.00400,0.03000),V(20.38500,2.12600,0.03000),V(20.31100,2.26400,0.03000),V(20.26500,2.41400,0.03000),V(20.25000,2.57000,0.03000),V(20.26500,2.72600,0.03000),V(20.31100,2.87600,0.03000),V(20.38500,3.01400,0.03000),V(20.48400,3.13600,0.03000),V(20.60600,3.23500,0.03000),V(20.74400,3.30900,0.03000),V(20.89400,3.35500,0.03000),V(21.05000,3.37000,0.03000),V(21.20600,3.35500,0.03000),V(21.35600,3.30900,0.03000),V(21.49400,3.23500,0.03000),V(21.61600,3.13600,0.03000),V(21.71500,3.01400,0.03000),V(21.78900,2.87600,0.03000),V(21.83500,2.72600,0.03000),V(21.85000,2.57000,0.03000),V(21.83500,2.41400,0.03000),V(21.78900,2.26400,0.03000),V(21.71500,2.12600,0.03000),V(21.61600,2.00400,0.03000),V(21.49400,1.90500,0.03000),V(21.35600,1.83100,0.03000),V(21.20600,1.78500,0.03000),V(21.05000,1.77000,0.03000)])]).extrude(V(0,0,0.01000)))
_s.append(Part.Face([_poly([V(23.74600,1.78500,0.03000),V(23.59000,1.77000,0.03000),V(23.43400,1.78500,0.03000),V(23.28400,1.83100,0.03000),V(23.14600,1.90500,0.03000),V(23.02400,2.00400,0.03000),V(22.92500,2.12600,0.03000),V(22.85100,2.26400,0.03000),V(22.80500,2.41400,0.03000),V(22.79000,2.57000,0.03000),V(22.80500,2.72600,0.03000),V(22.85100,2.87600,0.03000),V(22.92500,3.01400,0.03000),V(23.02400,3.13600,0.03000),V(23.14600,3.23500,0.03000),V(23.28400,3.30900,0.03000),V(23.43400,3.35500,0.03000),V(23.59000,3.37000,0.03000),V(23.74600,3.35500,0.03000),V(23.89600,3.30900,0.03000),V(24.03400,3.23500,0.03000),V(24.15600,3.13600,0.03000),V(24.25500,3.01400,0.03000),V(24.32900,2.87600,0.03000),V(24.37500,2.72600,0.03000),V(24.39000,2.57000,0.03000),V(24.37500,2.41400,0.03000),V(24.32900,2.26400,0.03000),V(24.25500,2.12600,0.03000),V(24.15600,2.00400,0.03000),V(24.03400,1.90500,0.03000),V(23.89600,1.83100,0.03000),V(23.74600,1.78500,0.03000)])]).extrude(V(0,0,0.01000)))
_s.append(Part.Face([_poly([V(13.58600,24.64500,0.03000),V(13.43000,24.63000,0.03000),V(13.27400,24.64500,0.03000),V(13.12400,24.69100,0.03000),V(12.98600,24.76500,0.03000),V(12.86400,24.86400,0.03000),V(12.76500,24.98600,0.03000),V(12.69100,25.12400,0.03000),V(12.64500,25.27400,0.03000),V(12.63000,25.43000,0.03000),V(12.64500,25.58600,0.03000),V(12.69100,25.73600,0.03000),V(12.76500,25.87400,0.03000),V(12.86400,25.99600,0.03000),V(12.98600,26.09500,0.03000),V(13.12400,26.16900,0.03000),V(13.27400,26.21500,0.03000),V(13.43000,26.23000,0.03000),V(13.58600,26.21500,0.03000),V(13.73600,26.16900,0.03000),V(13.87400,26.09500,0.03000),V(13.99600,25.99600,0.03000),V(14.09500,25.87400,0.03000),V(14.16900,25.73600,0.03000),V(14.21500,25.58600,0.03000),V(14.23000,25.43000,0.03000),V(14.21500,25.27400,0.03000),V(14.16900,25.12400,0.03000),V(14.09500,24.98600,0.03000),V(13.99600,24.86400,0.03000),V(13.87400,24.76500,0.03000),V(13.73600,24.69100,0.03000),V(13.58600,24.64500,0.03000)])]).extrude(V(0,0,0.01000)))
_s.append(Part.Face([_poly([V(3.27000,24.63000,0.03000),V(3.11400,24.64500,0.03000),V(2.96400,24.69100,0.03000),V(2.82600,24.76500,0.03000),V(2.70400,24.86400,0.03000),V(2.60500,24.98600,0.03000),V(2.53100,25.12400,0.03000),V(2.48500,25.27400,0.03000),V(2.47000,25.43000,0.03000),V(2.48500,25.58600,0.03000),V(2.53100,25.73600,0.03000),V(2.60500,25.87400,0.03000),V(2.70400,25.99600,0.03000),V(2.82600,26.09500,0.03000),V(2.96400,26.16900,0.03000),V(3.11400,26.21500,0.03000),V(3.27000,26.23000,0.03000),V(3.42600,26.21500,0.03000),V(3.57600,26.16900,0.03000),V(3.71400,26.09500,0.03000),V(3.83600,25.99600,0.03000),V(3.93500,25.87400,0.03000),V(4.00900,25.73600,0.03000),V(4.05500,25.58600,0.03000),V(4.07000,25.43000,0.03000),V(4.05500,25.27400,0.03000),V(4.00900,25.12400,0.03000),V(3.93500,24.98600,0.03000),V(3.83600,24.86400,0.03000),V(3.71400,24.76500,0.03000),V(3.57600,24.69100,0.03000),V(3.42600,24.64500,0.03000),V(3.27000,24.63000,0.03000)])]).extrude(V(0,0,0.01000)))
_s.append(Part.Face([_poly([V(16.12600,24.64500,0.03000),V(15.97000,24.63000,0.03000),V(15.81400,24.64500,0.03000),V(15.66400,24.69100,0.03000),V(15.52600,24.76500,0.03000),V(15.40400,24.86400,0.03000),V(15.30500,24.98600,0.03000),V(15.23100,25.12400,0.03000),V(15.18500,25.27400,0.03000),V(15.17000,25.43000,0.03000),V(15.18500,25.58600,0.03000),V(15.23100,25.73600,0.03000),V(15.30500,25.87400,0.03000),V(15.40400,25.99600,0.03000),V(15.52600,26.09500,0.03000),V(15.66400,26.16900,0.03000),V(15.81400,26.21500,0.03000),V(15.97000,26.23000,0.03000),V(16.12600,26.21500,0.03000),V(16.27600,26.16900,0.03000),V(16.41400,26.09500,0.03000),V(16.53600,25.99600,0.03000),V(16.63500,25.87400,0.03000),V(16.70900,25.73600,0.03000),V(16.75500,25.58600,0.03000),V(16.77000,25.43000,0.03000),V(16.75500,25.27400,0.03000),V(16.70900,25.12400,0.03000),V(16.63500,24.98600,0.03000),V(16.53600,24.86400,0.03000),V(16.41400,24.76500,0.03000),V(16.27600,24.69100,0.03000),V(16.12600,24.64500,0.03000)])]).extrude(V(0,0,0.01000)))
_s.append(Part.Face([_poly([V(5.81000,24.63000,0.03000),V(5.65400,24.64500,0.03000),V(5.50400,24.69100,0.03000),V(5.36600,24.76500,0.03000),V(5.24400,24.86400,0.03000),V(5.14500,24.98600,0.03000),V(5.07100,25.12400,0.03000),V(5.02500,25.27400,0.03000),V(5.01000,25.43000,0.03000),V(5.02500,25.58600,0.03000),V(5.07100,25.73600,0.03000),V(5.14500,25.87400,0.03000),V(5.24400,25.99600,0.03000),V(5.36600,26.09500,0.03000),V(5.50400,26.16900,0.03000),V(5.65400,26.21500,0.03000),V(5.81000,26.23000,0.03000),V(5.96600,26.21500,0.03000),V(6.11600,26.16900,0.03000),V(6.25400,26.09500,0.03000),V(6.37600,25.99600,0.03000),V(6.47500,25.87400,0.03000),V(6.54900,25.73600,0.03000),V(6.59500,25.58600,0.03000),V(6.61000,25.43000,0.03000),V(6.59500,25.27400,0.03000),V(6.54900,25.12400,0.03000),V(6.47500,24.98600,0.03000),V(6.37600,24.86400,0.03000),V(6.25400,24.76500,0.03000),V(6.11600,24.69100,0.03000),V(5.96600,24.64500,0.03000),V(5.81000,24.63000,0.03000)])]).extrude(V(0,0,0.01000)))
_s.append(Part.Face([_poly([V(18.66600,24.64500,0.03000),V(18.51000,24.63000,0.03000),V(18.35400,24.64500,0.03000),V(18.20400,24.69100,0.03000),V(18.06600,24.76500,0.03000),V(17.94400,24.86400,0.03000),V(17.84500,24.98600,0.03000),V(17.77100,25.12400,0.03000),V(17.72500,25.27400,0.03000),V(17.71000,25.43000,0.03000),V(17.72500,25.58600,0.03000),V(17.77100,25.73600,0.03000),V(17.84500,25.87400,0.03000),V(17.94400,25.99600,0.03000),V(18.06600,26.09500,0.03000),V(18.20400,26.16900,0.03000),V(18.35400,26.21500,0.03000),V(18.51000,26.23000,0.03000),V(18.66600,26.21500,0.03000),V(18.81600,26.16900,0.03000),V(18.95400,26.09500,0.03000),V(19.07600,25.99600,0.03000),V(19.17500,25.87400,0.03000),V(19.24900,25.73600,0.03000),V(19.29500,25.58600,0.03000),V(19.31000,25.43000,0.03000),V(19.29500,25.27400,0.03000),V(19.24900,25.12400,0.03000),V(19.17500,24.98600,0.03000),V(19.07600,24.86400,0.03000),V(18.95400,24.76500,0.03000),V(18.81600,24.69100,0.03000),V(18.66600,24.64500,0.03000)])]).extrude(V(0,0,0.01000)))
_s.append(Part.Face([_poly([V(8.35000,24.63000,0.03000),V(8.19400,24.64500,0.03000),V(8.04400,24.69100,0.03000),V(7.90600,24.76500,0.03000),V(7.78400,24.86400,0.03000),V(7.68500,24.98600,0.03000),V(7.61100,25.12400,0.03000),V(7.56500,25.27400,0.03000),V(7.55000,25.43000,0.03000),V(7.56500,25.58600,0.03000),V(7.61100,25.73600,0.03000),V(7.68500,25.87400,0.03000),V(7.78400,25.99600,0.03000),V(7.90600,26.09500,0.03000),V(8.04400,26.16900,0.03000),V(8.19400,26.21500,0.03000),V(8.35000,26.23000,0.03000),V(8.50600,26.21500,0.03000),V(8.65600,26.16900,0.03000),V(8.79400,26.09500,0.03000),V(8.91600,25.99600,0.03000),V(9.01500,25.87400,0.03000),V(9.08900,25.73600,0.03000),V(9.13500,25.58600,0.03000),V(9.15000,25.43000,0.03000),V(9.13500,25.27400,0.03000),V(9.08900,25.12400,0.03000),V(9.01500,24.98600,0.03000),V(8.91600,24.86400,0.03000),V(8.79400,24.76500,0.03000),V(8.65600,24.69100,0.03000),V(8.50600,24.64500,0.03000),V(8.35000,24.63000,0.03000)])]).extrude(V(0,0,0.01000)))
_s.append(Part.Face([_poly([V(21.05000,24.63000,0.03000),V(20.89400,24.64500,0.03000),V(20.74400,24.69100,0.03000),V(20.60600,24.76500,0.03000),V(20.48400,24.86400,0.03000),V(20.38500,24.98600,0.03000),V(20.31100,25.12400,0.03000),V(20.26500,25.27400,0.03000),V(20.25000,25.43000,0.03000),V(20.26500,25.58600,0.03000),V(20.31100,25.73600,0.03000),V(20.38500,25.87400,0.03000),V(20.48400,25.99600,0.03000),V(20.60600,26.09500,0.03000),V(20.74400,26.16900,0.03000),V(20.89400,26.21500,0.03000),V(21.05000,26.23000,0.03000),V(21.20600,26.21500,0.03000),V(21.35600,26.16900,0.03000),V(21.49400,26.09500,0.03000),V(21.61600,25.99600,0.03000),V(21.71500,25.87400,0.03000),V(21.78900,25.73600,0.03000),V(21.83500,25.58600,0.03000),V(21.85000,25.43000,0.03000),V(21.83500,25.27400,0.03000),V(21.78900,25.12400,0.03000),V(21.71500,24.98600,0.03000),V(21.61600,24.86400,0.03000),V(21.49400,24.76500,0.03000),V(21.35600,24.69100,0.03000),V(21.20600,24.64500,0.03000),V(21.05000,24.63000,0.03000)])]).extrude(V(0,0,0.01000)))
_s.append(Part.Face([_poly([V(11.04600,24.64500,0.03000),V(10.89000,24.63000,0.03000),V(10.73400,24.64500,0.03000),V(10.58400,24.69100,0.03000),V(10.44600,24.76500,0.03000),V(10.32400,24.86400,0.03000),V(10.22500,24.98600,0.03000),V(10.15100,25.12400,0.03000),V(10.10500,25.27400,0.03000),V(10.09000,25.43000,0.03000),V(10.10500,25.58600,0.03000),V(10.15100,25.73600,0.03000),V(10.22500,25.87400,0.03000),V(10.32400,25.99600,0.03000),V(10.44600,26.09500,0.03000),V(10.58400,26.16900,0.03000),V(10.73400,26.21500,0.03000),V(10.89000,26.23000,0.03000),V(11.04600,26.21500,0.03000),V(11.19600,26.16900,0.03000),V(11.33400,26.09500,0.03000),V(11.45600,25.99600,0.03000),V(11.55500,25.87400,0.03000),V(11.62900,25.73600,0.03000),V(11.67500,25.58600,0.03000),V(11.69000,25.43000,0.03000),V(11.67500,25.27400,0.03000),V(11.62900,25.12400,0.03000),V(11.55500,24.98600,0.03000),V(11.45600,24.86400,0.03000),V(11.33400,24.76500,0.03000),V(11.19600,24.69100,0.03000),V(11.04600,24.64500,0.03000)])]).extrude(V(0,0,0.01000)))
_s.append(Part.Face([_poly([V(23.59000,24.63000,0.03000),V(23.43400,24.64500,0.03000),V(23.28400,24.69100,0.03000),V(23.14600,24.76500,0.03000),V(23.02400,24.86400,0.03000),V(22.92500,24.98600,0.03000),V(22.85100,25.12400,0.03000),V(22.80500,25.27400,0.03000),V(22.79000,25.43000,0.03000),V(22.80500,25.58600,0.03000),V(22.85100,25.73600,0.03000),V(22.92500,25.87400,0.03000),V(23.02400,25.99600,0.03000),V(23.14600,26.09500,0.03000),V(23.28400,26.16900,0.03000),V(23.43400,26.21500,0.03000),V(23.59000,26.23000,0.03000),V(23.74600,26.21500,0.03000),V(23.89600,26.16900,0.03000),V(24.03400,26.09500,0.03000),V(24.15600,25.99600,0.03000),V(24.25500,25.87400,0.03000),V(24.32900,25.73600,0.03000),V(24.37500,25.58600,0.03000),V(24.39000,25.43000,0.03000),V(24.37500,25.27400,0.03000),V(24.32900,25.12400,0.03000),V(24.25500,24.98600,0.03000),V(24.15600,24.86400,0.03000),V(24.03400,24.76500,0.03000),V(23.89600,24.69100,0.03000),V(23.74600,24.64500,0.03000),V(23.59000,24.63000,0.03000)])]).extrude(V(0,0,0.01000)))
_s.append(Part.Face([_poly([V(48.44600,1.78500,0.03000),V(48.29000,1.77000,0.03000),V(48.13400,1.78500,0.03000),V(47.98400,1.83100,0.03000),V(47.84600,1.90500,0.03000),V(47.72400,2.00400,0.03000),V(47.62500,2.12600,0.03000),V(47.55100,2.26400,0.03000),V(47.50500,2.41400,0.03000),V(47.49000,2.57000,0.03000),V(47.50500,2.72600,0.03000),V(47.55100,2.87600,0.03000),V(47.62500,3.01400,0.03000),V(47.72400,3.13600,0.03000),V(47.84600,3.23500,0.03000),V(47.98400,3.30900,0.03000),V(48.13400,3.35500,0.03000),V(48.29000,3.37000,0.03000),V(48.44600,3.35500,0.03000),V(48.59600,3.30900,0.03000),V(48.73400,3.23500,0.03000),V(48.85600,3.13600,0.03000),V(48.95500,3.01400,0.03000),V(49.02900,2.87600,0.03000),V(49.07500,2.72600,0.03000),V(49.09000,2.57000,0.03000),V(49.07500,2.41400,0.03000),V(49.02900,2.26400,0.03000),V(48.95500,2.12600,0.03000),V(48.85600,2.00400,0.03000),V(48.73400,1.90500,0.03000),V(48.59600,1.83100,0.03000),V(48.44600,1.78500,0.03000)])]).extrude(V(0,0,0.01000)))
_s.append(Part.Face([_poly([V(26.28600,1.78500,0.03000),V(26.13000,1.77000,0.03000),V(25.97400,1.78500,0.03000),V(25.82400,1.83100,0.03000),V(25.68600,1.90500,0.03000),V(25.56400,2.00400,0.03000),V(25.46500,2.12600,0.03000),V(25.39100,2.26400,0.03000),V(25.34500,2.41400,0.03000),V(25.33000,2.57000,0.03000),V(25.34500,2.72600,0.03000),V(25.39100,2.87600,0.03000),V(25.46500,3.01400,0.03000),V(25.56400,3.13600,0.03000),V(25.68600,3.23500,0.03000),V(25.82400,3.30900,0.03000),V(25.97400,3.35500,0.03000),V(26.13000,3.37000,0.03000),V(26.28600,3.35500,0.03000),V(26.43600,3.30900,0.03000),V(26.57400,3.23500,0.03000),V(26.69600,3.13600,0.03000),V(26.79500,3.01400,0.03000),V(26.86900,2.87600,0.03000),V(26.91500,2.72600,0.03000),V(26.93000,2.57000,0.03000),V(26.91500,2.41400,0.03000),V(26.86900,2.26400,0.03000),V(26.79500,2.12600,0.03000),V(26.69600,2.00400,0.03000),V(26.57400,1.90500,0.03000),V(26.43600,1.83100,0.03000),V(26.28600,1.78500,0.03000)])]).extrude(V(0,0,0.01000)))
_s.append(Part.Face([_poly([V(40.67000,1.77000,0.03000),V(40.51400,1.78500,0.03000),V(40.36400,1.83100,0.03000),V(40.22600,1.90500,0.03000),V(40.10400,2.00400,0.03000),V(40.00500,2.12600,0.03000),V(39.93100,2.26400,0.03000),V(39.88500,2.41400,0.03000),V(39.87000,2.57000,0.03000),V(39.88500,2.72600,0.03000),V(39.93100,2.87600,0.03000),V(40.00500,3.01400,0.03000),V(40.10400,3.13600,0.03000),V(40.22600,3.23500,0.03000),V(40.36400,3.30900,0.03000),V(40.51400,3.35500,0.03000),V(40.67000,3.37000,0.03000),V(40.82600,3.35500,0.03000),V(40.97600,3.30900,0.03000),V(41.11400,3.23500,0.03000),V(41.23600,3.13600,0.03000),V(41.33500,3.01400,0.03000),V(41.40900,2.87600,0.03000),V(41.45500,2.72600,0.03000),V(41.47000,2.57000,0.03000),V(41.45500,2.41400,0.03000),V(41.40900,2.26400,0.03000),V(41.33500,2.12600,0.03000),V(41.23600,2.00400,0.03000),V(41.11400,1.90500,0.03000),V(40.97600,1.83100,0.03000),V(40.82600,1.78500,0.03000),V(40.67000,1.77000,0.03000)])]).extrude(V(0,0,0.01000)))
_s.append(Part.Face([_poly([V(45.90600,1.78500,0.03000),V(45.75000,1.77000,0.03000),V(45.59400,1.78500,0.03000),V(45.44400,1.83100,0.03000),V(45.30600,1.90500,0.03000),V(45.18400,2.00400,0.03000),V(45.08500,2.12600,0.03000),V(45.01100,2.26400,0.03000),V(44.96500,2.41400,0.03000),V(44.95000,2.57000,0.03000),V(44.96500,2.72600,0.03000),V(45.01100,2.87600,0.03000),V(45.08500,3.01400,0.03000),V(45.18400,3.13600,0.03000),V(45.30600,3.23500,0.03000),V(45.44400,3.30900,0.03000),V(45.59400,3.35500,0.03000),V(45.75000,3.37000,0.03000),V(45.90600,3.35500,0.03000),V(46.05600,3.30900,0.03000),V(46.19400,3.23500,0.03000),V(46.31600,3.13600,0.03000),V(46.41500,3.01400,0.03000),V(46.48900,2.87600,0.03000),V(46.53500,2.72600,0.03000),V(46.55000,2.57000,0.03000),V(46.53500,2.41400,0.03000),V(46.48900,2.26400,0.03000),V(46.41500,2.12600,0.03000),V(46.31600,2.00400,0.03000),V(46.19400,1.90500,0.03000),V(46.05600,1.83100,0.03000),V(45.90600,1.78500,0.03000)])]).extrude(V(0,0,0.01000)))
_s.append(Part.Face([_poly([V(43.21000,1.77000,0.03000),V(43.05400,1.78500,0.03000),V(42.90400,1.83100,0.03000),V(42.76600,1.90500,0.03000),V(42.64400,2.00400,0.03000),V(42.54500,2.12600,0.03000),V(42.47100,2.26400,0.03000),V(42.42500,2.41400,0.03000),V(42.41000,2.57000,0.03000),V(42.42500,2.72600,0.03000),V(42.47100,2.87600,0.03000),V(42.54500,3.01400,0.03000),V(42.64400,3.13600,0.03000),V(42.76600,3.23500,0.03000),V(42.90400,3.30900,0.03000),V(43.05400,3.35500,0.03000),V(43.21000,3.37000,0.03000),V(43.36600,3.35500,0.03000),V(43.51600,3.30900,0.03000),V(43.65400,3.23500,0.03000),V(43.77600,3.13600,0.03000),V(43.87500,3.01400,0.03000),V(43.94900,2.87600,0.03000),V(43.99500,2.72600,0.03000),V(44.01000,2.57000,0.03000),V(43.99500,2.41400,0.03000),V(43.94900,2.26400,0.03000),V(43.87500,2.12600,0.03000),V(43.77600,2.00400,0.03000),V(43.65400,1.90500,0.03000),V(43.51600,1.83100,0.03000),V(43.36600,1.78500,0.03000),V(43.21000,1.77000,0.03000)])]).extrude(V(0,0,0.01000)))
_s.append(Part.Face([_poly([V(50.98600,1.78500,0.03000),V(50.83000,1.77000,0.03000),V(50.67400,1.78500,0.03000),V(50.52400,1.83100,0.03000),V(50.38600,1.90500,0.03000),V(50.26400,2.00400,0.03000),V(50.16500,2.12600,0.03000),V(50.09100,2.26400,0.03000),V(50.04500,2.41400,0.03000),V(50.03000,2.57000,0.03000),V(50.04500,2.72600,0.03000),V(50.09100,2.87600,0.03000),V(50.16500,3.01400,0.03000),V(50.26400,3.13600,0.03000),V(50.38600,3.23500,0.03000),V(50.52400,3.30900,0.03000),V(50.67400,3.35500,0.03000),V(50.83000,3.37000,0.03000),V(50.98600,3.35500,0.03000),V(51.13600,3.30900,0.03000),V(51.27400,3.23500,0.03000),V(51.39600,3.13600,0.03000),V(51.49500,3.01400,0.03000),V(51.56900,2.87600,0.03000),V(51.61500,2.72600,0.03000),V(51.63000,2.57000,0.03000),V(51.61500,2.41400,0.03000),V(51.56900,2.26400,0.03000),V(51.49500,2.12600,0.03000),V(51.39600,2.00400,0.03000),V(51.27400,1.90500,0.03000),V(51.13600,1.83100,0.03000),V(50.98600,1.78500,0.03000)])]).extrude(V(0,0,0.01000)))
_s.append(Part.Face([_poly([V(53.37000,1.77000,0.03000),V(53.21400,1.78500,0.03000),V(53.06400,1.83100,0.03000),V(52.92600,1.90500,0.03000),V(52.80400,2.00400,0.03000),V(52.70500,2.12600,0.03000),V(52.63100,2.26400,0.03000),V(52.58500,2.41400,0.03000),V(52.57000,2.57000,0.03000),V(52.58500,2.72600,0.03000),V(52.63100,2.87600,0.03000),V(52.70500,3.01400,0.03000),V(52.80400,3.13600,0.03000),V(52.92600,3.23500,0.03000),V(53.06400,3.30900,0.03000),V(53.21400,3.35500,0.03000),V(53.37000,3.37000,0.03000),V(53.52600,3.35500,0.03000),V(53.67600,3.30900,0.03000),V(53.81400,3.23500,0.03000),V(53.93600,3.13600,0.03000),V(54.03500,3.01400,0.03000),V(54.10900,2.87600,0.03000),V(54.15500,2.72600,0.03000),V(54.17000,2.57000,0.03000),V(54.15500,2.41400,0.03000),V(54.10900,2.26400,0.03000),V(54.03500,2.12600,0.03000),V(53.93600,2.00400,0.03000),V(53.81400,1.90500,0.03000),V(53.67600,1.83100,0.03000),V(53.52600,1.78500,0.03000),V(53.37000,1.77000,0.03000)])]).extrude(V(0,0,0.01000)))
_s.append(Part.Face([_poly([V(55.91000,1.77000,0.03000),V(55.75400,1.78500,0.03000),V(55.60400,1.83100,0.03000),V(55.46600,1.90500,0.03000),V(55.34400,2.00400,0.03000),V(55.24500,2.12600,0.03000),V(55.17100,2.26400,0.03000),V(55.12500,2.41400,0.03000),V(55.11000,2.57000,0.03000),V(55.12500,2.72600,0.03000),V(55.17100,2.87600,0.03000),V(55.24500,3.01400,0.03000),V(55.34400,3.13600,0.03000),V(55.46600,3.23500,0.03000),V(55.60400,3.30900,0.03000),V(55.75400,3.35500,0.03000),V(55.91000,3.37000,0.03000),V(56.06600,3.35500,0.03000),V(56.21600,3.30900,0.03000),V(56.35400,3.23500,0.03000),V(56.47600,3.13600,0.03000),V(56.57500,3.01400,0.03000),V(56.64900,2.87600,0.03000),V(56.69500,2.72600,0.03000),V(56.71000,2.57000,0.03000),V(56.69500,2.41400,0.03000),V(56.64900,2.26400,0.03000),V(56.57500,2.12600,0.03000),V(56.47600,2.00400,0.03000),V(56.35400,1.90500,0.03000),V(56.21600,1.83100,0.03000),V(56.06600,1.78500,0.03000),V(55.91000,1.77000,0.03000)])]).extrude(V(0,0,0.01000)))
_s.append(Part.Face([_poly([V(58.60600,1.78500,0.03000),V(58.45000,1.77000,0.03000),V(58.29400,1.78500,0.03000),V(58.14400,1.83100,0.03000),V(58.00600,1.90500,0.03000),V(57.88400,2.00400,0.03000),V(57.78500,2.12600,0.03000),V(57.71100,2.26400,0.03000),V(57.66500,2.41400,0.03000),V(57.65000,2.57000,0.03000),V(57.66500,2.72600,0.03000),V(57.71100,2.87600,0.03000),V(57.78500,3.01400,0.03000),V(57.88400,3.13600,0.03000),V(58.00600,3.23500,0.03000),V(58.14400,3.30900,0.03000),V(58.29400,3.35500,0.03000),V(58.45000,3.37000,0.03000),V(58.60600,3.35500,0.03000),V(58.75600,3.30900,0.03000),V(58.89400,3.23500,0.03000),V(59.01600,3.13600,0.03000),V(59.11500,3.01400,0.03000),V(59.18900,2.87600,0.03000),V(59.23500,2.72600,0.03000),V(59.25000,2.57000,0.03000),V(59.23500,2.41400,0.03000),V(59.18900,2.26400,0.03000),V(59.11500,2.12600,0.03000),V(59.01600,2.00400,0.03000),V(58.89400,1.90500,0.03000),V(58.75600,1.83100,0.03000),V(58.60600,1.78500,0.03000)])]).extrude(V(0,0,0.01000)))
_s.append(Part.Face([_poly([V(48.29000,24.63000,0.03000),V(48.13400,24.64500,0.03000),V(47.98400,24.69100,0.03000),V(47.84600,24.76500,0.03000),V(47.72400,24.86400,0.03000),V(47.62500,24.98600,0.03000),V(47.55100,25.12400,0.03000),V(47.50500,25.27400,0.03000),V(47.49000,25.43000,0.03000),V(47.50500,25.58600,0.03000),V(47.55100,25.73600,0.03000),V(47.62500,25.87400,0.03000),V(47.72400,25.99600,0.03000),V(47.84600,26.09500,0.03000),V(47.98400,26.16900,0.03000),V(48.13400,26.21500,0.03000),V(48.29000,26.23000,0.03000),V(48.44600,26.21500,0.03000),V(48.59600,26.16900,0.03000),V(48.73400,26.09500,0.03000),V(48.85600,25.99600,0.03000),V(48.95500,25.87400,0.03000),V(49.02900,25.73600,0.03000),V(49.07500,25.58600,0.03000),V(49.09000,25.43000,0.03000),V(49.07500,25.27400,0.03000),V(49.02900,25.12400,0.03000),V(48.95500,24.98600,0.03000),V(48.85600,24.86400,0.03000),V(48.73400,24.76500,0.03000),V(48.59600,24.69100,0.03000),V(48.44600,24.64500,0.03000),V(48.29000,24.63000,0.03000)])]).extrude(V(0,0,0.01000)))
_s.append(Part.Face([_poly([V(50.98600,24.64500,0.03000),V(50.83000,24.63000,0.03000),V(50.67400,24.64500,0.03000),V(50.52400,24.69100,0.03000),V(50.38600,24.76500,0.03000),V(50.26400,24.86400,0.03000),V(50.16500,24.98600,0.03000),V(50.09100,25.12400,0.03000),V(50.04500,25.27400,0.03000),V(50.03000,25.43000,0.03000),V(50.04500,25.58600,0.03000),V(50.09100,25.73600,0.03000),V(50.16500,25.87400,0.03000),V(50.26400,25.99600,0.03000),V(50.38600,26.09500,0.03000),V(50.52400,26.16900,0.03000),V(50.67400,26.21500,0.03000),V(50.83000,26.23000,0.03000),V(50.98600,26.21500,0.03000),V(51.13600,26.16900,0.03000),V(51.27400,26.09500,0.03000),V(51.39600,25.99600,0.03000),V(51.49500,25.87400,0.03000),V(51.56900,25.73600,0.03000),V(51.61500,25.58600,0.03000),V(51.63000,25.43000,0.03000),V(51.61500,25.27400,0.03000),V(51.56900,25.12400,0.03000),V(51.49500,24.98600,0.03000),V(51.39600,24.86400,0.03000),V(51.27400,24.76500,0.03000),V(51.13600,24.69100,0.03000),V(50.98600,24.64500,0.03000)])]).extrude(V(0,0,0.01000)))
_s.append(Part.Face([_poly([V(26.13000,24.63000,0.03000),V(25.97400,24.64500,0.03000),V(25.82400,24.69100,0.03000),V(25.68600,24.76500,0.03000),V(25.56400,24.86400,0.03000),V(25.46500,24.98600,0.03000),V(25.39100,25.12400,0.03000),V(25.34500,25.27400,0.03000),V(25.33000,25.43000,0.03000),V(25.34500,25.58600,0.03000),V(25.39100,25.73600,0.03000),V(25.46500,25.87400,0.03000),V(25.56400,25.99600,0.03000),V(25.68600,26.09500,0.03000),V(25.82400,26.16900,0.03000),V(25.97400,26.21500,0.03000),V(26.13000,26.23000,0.03000),V(26.28600,26.21500,0.03000),V(26.43600,26.16900,0.03000),V(26.57400,26.09500,0.03000),V(26.69600,25.99600,0.03000),V(26.79500,25.87400,0.03000),V(26.86900,25.73600,0.03000),V(26.91500,25.58600,0.03000),V(26.93000,25.43000,0.03000),V(26.91500,25.27400,0.03000),V(26.86900,25.12400,0.03000),V(26.79500,24.98600,0.03000),V(26.69600,24.86400,0.03000),V(26.57400,24.76500,0.03000),V(26.43600,24.69100,0.03000),V(26.28600,24.64500,0.03000),V(26.13000,24.63000,0.03000)])]).extrude(V(0,0,0.01000)))
_s.append(Part.Face([_poly([V(53.52600,24.64500,0.03000),V(53.37000,24.63000,0.03000),V(53.21400,24.64500,0.03000),V(53.06400,24.69100,0.03000),V(52.92600,24.76500,0.03000),V(52.80400,24.86400,0.03000),V(52.70500,24.98600,0.03000),V(52.63100,25.12400,0.03000),V(52.58500,25.27400,0.03000),V(52.57000,25.43000,0.03000),V(52.58500,25.58600,0.03000),V(52.63100,25.73600,0.03000),V(52.70500,25.87400,0.03000),V(52.80400,25.99600,0.03000),V(52.92600,26.09500,0.03000),V(53.06400,26.16900,0.03000),V(53.21400,26.21500,0.03000),V(53.37000,26.23000,0.03000),V(53.52600,26.21500,0.03000),V(53.67600,26.16900,0.03000),V(53.81400,26.09500,0.03000),V(53.93600,25.99600,0.03000),V(54.03500,25.87400,0.03000),V(54.10900,25.73600,0.03000),V(54.15500,25.58600,0.03000),V(54.17000,25.43000,0.03000),V(54.15500,25.27400,0.03000),V(54.10900,25.12400,0.03000),V(54.03500,24.98600,0.03000),V(53.93600,24.86400,0.03000),V(53.81400,24.76500,0.03000),V(53.67600,24.69100,0.03000),V(53.52600,24.64500,0.03000)])]).extrude(V(0,0,0.01000)))
_s.append(Part.Face([_poly([V(40.67000,24.63000,0.03000),V(40.51400,24.64500,0.03000),V(40.36400,24.69100,0.03000),V(40.22600,24.76500,0.03000),V(40.10400,24.86400,0.03000),V(40.00500,24.98600,0.03000),V(39.93100,25.12400,0.03000),V(39.88500,25.27400,0.03000),V(39.87000,25.43000,0.03000),V(39.88500,25.58600,0.03000),V(39.93100,25.73600,0.03000),V(40.00500,25.87400,0.03000),V(40.10400,25.99600,0.03000),V(40.22600,26.09500,0.03000),V(40.36400,26.16900,0.03000),V(40.51400,26.21500,0.03000),V(40.67000,26.23000,0.03000),V(40.82600,26.21500,0.03000),V(40.97600,26.16900,0.03000),V(41.11400,26.09500,0.03000),V(41.23600,25.99600,0.03000),V(41.33500,25.87400,0.03000),V(41.40900,25.73600,0.03000),V(41.45500,25.58600,0.03000),V(41.47000,25.43000,0.03000),V(41.45500,25.27400,0.03000),V(41.40900,25.12400,0.03000),V(41.33500,24.98600,0.03000),V(41.23600,24.86400,0.03000),V(41.11400,24.76500,0.03000),V(40.97600,24.69100,0.03000),V(40.82600,24.64500,0.03000),V(40.67000,24.63000,0.03000)])]).extrude(V(0,0,0.01000)))
_s.append(Part.Face([_poly([V(43.36600,24.64500,0.03000),V(43.21000,24.63000,0.03000),V(43.05400,24.64500,0.03000),V(42.90400,24.69100,0.03000),V(42.76600,24.76500,0.03000),V(42.64400,24.86400,0.03000),V(42.54500,24.98600,0.03000),V(42.47100,25.12400,0.03000),V(42.42500,25.27400,0.03000),V(42.41000,25.43000,0.03000),V(42.42500,25.58600,0.03000),V(42.47100,25.73600,0.03000),V(42.54500,25.87400,0.03000),V(42.64400,25.99600,0.03000),V(42.76600,26.09500,0.03000),V(42.90400,26.16900,0.03000),V(43.05400,26.21500,0.03000),V(43.21000,26.23000,0.03000),V(43.36600,26.21500,0.03000),V(43.51600,26.16900,0.03000),V(43.65400,26.09500,0.03000),V(43.77600,25.99600,0.03000),V(43.87500,25.87400,0.03000),V(43.94900,25.73600,0.03000),V(43.99500,25.58600,0.03000),V(44.01000,25.43000,0.03000),V(43.99500,25.27400,0.03000),V(43.94900,25.12400,0.03000),V(43.87500,24.98600,0.03000),V(43.77600,24.86400,0.03000),V(43.65400,24.76500,0.03000),V(43.51600,24.69100,0.03000),V(43.36600,24.64500,0.03000)])]).extrude(V(0,0,0.01000)))
_s.append(Part.Face([_poly([V(55.91000,24.63000,0.03000),V(55.75400,24.64500,0.03000),V(55.60400,24.69100,0.03000),V(55.46600,24.76500,0.03000),V(55.34400,24.86400,0.03000),V(55.24500,24.98600,0.03000),V(55.17100,25.12400,0.03000),V(55.12500,25.27400,0.03000),V(55.11000,25.43000,0.03000),V(55.12500,25.58600,0.03000),V(55.17100,25.73600,0.03000),V(55.24500,25.87400,0.03000),V(55.34400,25.99600,0.03000),V(55.46600,26.09500,0.03000),V(55.60400,26.16900,0.03000),V(55.75400,26.21500,0.03000),V(55.91000,26.23000,0.03000),V(56.06600,26.21500,0.03000),V(56.21600,26.16900,0.03000),V(56.35400,26.09500,0.03000),V(56.47600,25.99600,0.03000),V(56.57500,25.87400,0.03000),V(56.64900,25.73600,0.03000),V(56.69500,25.58600,0.03000),V(56.71000,25.43000,0.03000),V(56.69500,25.27400,0.03000),V(56.64900,25.12400,0.03000),V(56.57500,24.98600,0.03000),V(56.47600,24.86400,0.03000),V(56.35400,24.76500,0.03000),V(56.21600,24.69100,0.03000),V(56.06600,24.64500,0.03000),V(55.91000,24.63000,0.03000)])]).extrude(V(0,0,0.01000)))
_s.append(Part.Face([_poly([V(45.90600,24.64500,0.03000),V(45.75000,24.63000,0.03000),V(45.59400,24.64500,0.03000),V(45.44400,24.69100,0.03000),V(45.30600,24.76500,0.03000),V(45.18400,24.86400,0.03000),V(45.08500,24.98600,0.03000),V(45.01100,25.12400,0.03000),V(44.96500,25.27400,0.03000),V(44.95000,25.43000,0.03000),V(44.96500,25.58600,0.03000),V(45.01100,25.73600,0.03000),V(45.08500,25.87400,0.03000),V(45.18400,25.99600,0.03000),V(45.30600,26.09500,0.03000),V(45.44400,26.16900,0.03000),V(45.59400,26.21500,0.03000),V(45.75000,26.23000,0.03000),V(45.90600,26.21500,0.03000),V(46.05600,26.16900,0.03000),V(46.19400,26.09500,0.03000),V(46.31600,25.99600,0.03000),V(46.41500,25.87400,0.03000),V(46.48900,25.73600,0.03000),V(46.53500,25.58600,0.03000),V(46.55000,25.43000,0.03000),V(46.53500,25.27400,0.03000),V(46.48900,25.12400,0.03000),V(46.41500,24.98600,0.03000),V(46.31600,24.86400,0.03000),V(46.19400,24.76500,0.03000),V(46.05600,24.69100,0.03000),V(45.90600,24.64500,0.03000)])]).extrude(V(0,0,0.01000)))
_s.append(Part.Face([_poly([V(58.45000,24.63000,0.03000),V(58.29400,24.64500,0.03000),V(58.14400,24.69100,0.03000),V(58.00600,24.76500,0.03000),V(57.88400,24.86400,0.03000),V(57.78500,24.98600,0.03000),V(57.71100,25.12400,0.03000),V(57.66500,25.27400,0.03000),V(57.65000,25.43000,0.03000),V(57.66500,25.58600,0.03000),V(57.71100,25.73600,0.03000),V(57.78500,25.87400,0.03000),V(57.88400,25.99600,0.03000),V(58.00600,26.09500,0.03000),V(58.14400,26.16900,0.03000),V(58.29400,26.21500,0.03000),V(58.45000,26.23000,0.03000),V(58.60600,26.21500,0.03000),V(58.75600,26.16900,0.03000),V(58.89400,26.09500,0.03000),V(59.01600,25.99600,0.03000),V(59.11500,25.87400,0.03000),V(59.18900,25.73600,0.03000),V(59.23500,25.58600,0.03000),V(59.25000,25.43000,0.03000),V(59.23500,25.27400,0.03000),V(59.18900,25.12400,0.03000),V(59.11500,24.98600,0.03000),V(59.01600,24.86400,0.03000),V(58.89400,24.76500,0.03000),V(58.75600,24.69100,0.03000),V(58.60600,24.64500,0.03000),V(58.45000,24.63000,0.03000)])]).extrude(V(0,0,0.01000)))
_s.append(Part.Face([_poly([V(60.99000,1.77000,0.03000),V(60.83400,1.78500,0.03000),V(60.68400,1.83100,0.03000),V(60.54600,1.90500,0.03000),V(60.42400,2.00400,0.03000),V(60.32500,2.12600,0.03000),V(60.25100,2.26400,0.03000),V(60.20500,2.41400,0.03000),V(60.19000,2.57000,0.03000),V(60.20500,2.72600,0.03000),V(60.25100,2.87600,0.03000),V(60.32500,3.01400,0.03000),V(60.42400,3.13600,0.03000),V(60.54600,3.23500,0.03000),V(60.68400,3.30900,0.03000),V(60.83400,3.35500,0.03000),V(60.99000,3.37000,0.03000),V(61.14600,3.35500,0.03000),V(61.29600,3.30900,0.03000),V(61.43400,3.23500,0.03000),V(61.55600,3.13600,0.03000),V(61.65500,3.01400,0.03000),V(61.72900,2.87600,0.03000),V(61.77500,2.72600,0.03000),V(61.79000,2.57000,0.03000),V(61.77500,2.41400,0.03000),V(61.72900,2.26400,0.03000),V(61.65500,2.12600,0.03000),V(61.55600,2.00400,0.03000),V(61.43400,1.90500,0.03000),V(61.29600,1.83100,0.03000),V(61.14600,1.78500,0.03000),V(60.99000,1.77000,0.03000)])]).extrude(V(0,0,0.01000)))
_s.append(Part.Face([_poly([V(71.15000,1.77000,0.03000),V(70.99400,1.78500,0.03000),V(70.84400,1.83100,0.03000),V(70.70600,1.90500,0.03000),V(70.58400,2.00400,0.03000),V(70.48500,2.12600,0.03000),V(70.41100,2.26400,0.03000),V(70.36500,2.41400,0.03000),V(70.35000,2.57000,0.03000),V(70.36500,2.72600,0.03000),V(70.41100,2.87600,0.03000),V(70.48500,3.01400,0.03000),V(70.58400,3.13600,0.03000),V(70.70600,3.23500,0.03000),V(70.84400,3.30900,0.03000),V(70.99400,3.35500,0.03000),V(71.15000,3.37000,0.03000),V(71.30600,3.35500,0.03000),V(71.45600,3.30900,0.03000),V(71.59400,3.23500,0.03000),V(71.71600,3.13600,0.03000),V(71.81500,3.01400,0.03000),V(71.88900,2.87600,0.03000),V(71.93500,2.72600,0.03000),V(71.95000,2.57000,0.03000),V(71.93500,2.41400,0.03000),V(71.88900,2.26400,0.03000),V(71.81500,2.12600,0.03000),V(71.71600,2.00400,0.03000),V(71.59400,1.90500,0.03000),V(71.45600,1.83100,0.03000),V(71.30600,1.78500,0.03000),V(71.15000,1.77000,0.03000)])]).extrude(V(0,0,0.01000)))
_s.append(Part.Face([_poly([V(68.61000,1.77000,0.03000),V(68.45400,1.78500,0.03000),V(68.30400,1.83100,0.03000),V(68.16600,1.90500,0.03000),V(68.04400,2.00400,0.03000),V(67.94500,2.12600,0.03000),V(67.87100,2.26400,0.03000),V(67.82500,2.41400,0.03000),V(67.81000,2.57000,0.03000),V(67.82500,2.72600,0.03000),V(67.87100,2.87600,0.03000),V(67.94500,3.01400,0.03000),V(68.04400,3.13600,0.03000),V(68.16600,3.23500,0.03000),V(68.30400,3.30900,0.03000),V(68.45400,3.35500,0.03000),V(68.61000,3.37000,0.03000),V(68.76600,3.35500,0.03000),V(68.91600,3.30900,0.03000),V(69.05400,3.23500,0.03000),V(69.17600,3.13600,0.03000),V(69.27500,3.01400,0.03000),V(69.34900,2.87600,0.03000),V(69.39500,2.72600,0.03000),V(69.41000,2.57000,0.03000),V(69.39500,2.41400,0.03000),V(69.34900,2.26400,0.03000),V(69.27500,2.12600,0.03000),V(69.17600,2.00400,0.03000),V(69.05400,1.90500,0.03000),V(68.91600,1.83100,0.03000),V(68.76600,1.78500,0.03000),V(68.61000,1.77000,0.03000)])]).extrude(V(0,0,0.01000)))
_s.append(Part.Face([_poly([V(63.68600,1.78500,0.03000),V(63.53000,1.77000,0.03000),V(63.37400,1.78500,0.03000),V(63.22400,1.83100,0.03000),V(63.08600,1.90500,0.03000),V(62.96400,2.00400,0.03000),V(62.86500,2.12600,0.03000),V(62.79100,2.26400,0.03000),V(62.74500,2.41400,0.03000),V(62.73000,2.57000,0.03000),V(62.74500,2.72600,0.03000),V(62.79100,2.87600,0.03000),V(62.86500,3.01400,0.03000),V(62.96400,3.13600,0.03000),V(63.08600,3.23500,0.03000),V(63.22400,3.30900,0.03000),V(63.37400,3.35500,0.03000),V(63.53000,3.37000,0.03000),V(63.68600,3.35500,0.03000),V(63.83600,3.30900,0.03000),V(63.97400,3.23500,0.03000),V(64.09600,3.13600,0.03000),V(64.19500,3.01400,0.03000),V(64.26900,2.87600,0.03000),V(64.31500,2.72600,0.03000),V(64.33000,2.57000,0.03000),V(64.31500,2.41400,0.03000),V(64.26900,2.26400,0.03000),V(64.19500,2.12600,0.03000),V(64.09600,2.00400,0.03000),V(63.97400,1.90500,0.03000),V(63.83600,1.83100,0.03000),V(63.68600,1.78500,0.03000)])]).extrude(V(0,0,0.01000)))
_s.append(Part.Face([_poly([V(66.22600,1.78500,0.03000),V(66.07000,1.77000,0.03000),V(65.91400,1.78500,0.03000),V(65.76400,1.83100,0.03000),V(65.62600,1.90500,0.03000),V(65.50400,2.00400,0.03000),V(65.40500,2.12600,0.03000),V(65.33100,2.26400,0.03000),V(65.28500,2.41400,0.03000),V(65.27000,2.57000,0.03000),V(65.28500,2.72600,0.03000),V(65.33100,2.87600,0.03000),V(65.40500,3.01400,0.03000),V(65.50400,3.13600,0.03000),V(65.62600,3.23500,0.03000),V(65.76400,3.30900,0.03000),V(65.91400,3.35500,0.03000),V(66.07000,3.37000,0.03000),V(66.22600,3.35500,0.03000),V(66.37600,3.30900,0.03000),V(66.51400,3.23500,0.03000),V(66.63600,3.13600,0.03000),V(66.73500,3.01400,0.03000),V(66.80900,2.87600,0.03000),V(66.85500,2.72600,0.03000),V(66.87000,2.57000,0.03000),V(66.85500,2.41400,0.03000),V(66.80900,2.26400,0.03000),V(66.73500,2.12600,0.03000),V(66.63600,2.00400,0.03000),V(66.51400,1.90500,0.03000),V(66.37600,1.83100,0.03000),V(66.22600,1.78500,0.03000)])]).extrude(V(0,0,0.01000)))
_s.append(Part.Face([_poly([V(73.69000,1.77000,0.03000),V(73.53400,1.78500,0.03000),V(73.38400,1.83100,0.03000),V(73.24600,1.90500,0.03000),V(73.12400,2.00400,0.03000),V(73.02500,2.12600,0.03000),V(72.95100,2.26400,0.03000),V(72.90500,2.41400,0.03000),V(72.89000,2.57000,0.03000),V(72.90500,2.72600,0.03000),V(72.95100,2.87600,0.03000),V(73.02500,3.01400,0.03000),V(73.12400,3.13600,0.03000),V(73.24600,3.23500,0.03000),V(73.38400,3.30900,0.03000),V(73.53400,3.35500,0.03000),V(73.69000,3.37000,0.03000),V(73.84600,3.35500,0.03000),V(73.99600,3.30900,0.03000),V(74.13400,3.23500,0.03000),V(74.25600,3.13600,0.03000),V(74.35500,3.01400,0.03000),V(74.42900,2.87600,0.03000),V(74.47500,2.72600,0.03000),V(74.49000,2.57000,0.03000),V(74.47500,2.41400,0.03000),V(74.42900,2.26400,0.03000),V(74.35500,2.12600,0.03000),V(74.25600,2.00400,0.03000),V(74.13400,1.90500,0.03000),V(73.99600,1.83100,0.03000),V(73.84600,1.78500,0.03000),V(73.69000,1.77000,0.03000)])]).extrude(V(0,0,0.01000)))
_s.append(Part.Face([_poly([V(76.38600,1.78500,0.03000),V(76.23000,1.77000,0.03000),V(76.07400,1.78500,0.03000),V(75.92400,1.83100,0.03000),V(75.78600,1.90500,0.03000),V(75.66400,2.00400,0.03000),V(75.56500,2.12600,0.03000),V(75.49100,2.26400,0.03000),V(75.44500,2.41400,0.03000),V(75.43000,2.57000,0.03000),V(75.44500,2.72600,0.03000),V(75.49100,2.87600,0.03000),V(75.56500,3.01400,0.03000),V(75.66400,3.13600,0.03000),V(75.78600,3.23500,0.03000),V(75.92400,3.30900,0.03000),V(76.07400,3.35500,0.03000),V(76.23000,3.37000,0.03000),V(76.38600,3.35500,0.03000),V(76.53600,3.30900,0.03000),V(76.67400,3.23500,0.03000),V(76.79600,3.13600,0.03000),V(76.89500,3.01400,0.03000),V(76.96900,2.87600,0.03000),V(77.01500,2.72600,0.03000),V(77.03000,2.57000,0.03000),V(77.01500,2.41400,0.03000),V(76.96900,2.26400,0.03000),V(76.89500,2.12600,0.03000),V(76.79600,2.00400,0.03000),V(76.67400,1.90500,0.03000),V(76.53600,1.83100,0.03000),V(76.38600,1.78500,0.03000)])]).extrude(V(0,0,0.01000)))
_s.append(Part.Face([_poly([V(90.77000,1.77000,0.03000),V(90.61400,1.78500,0.03000),V(90.46400,1.83100,0.03000),V(90.32600,1.90500,0.03000),V(90.20400,2.00400,0.03000),V(90.10500,2.12600,0.03000),V(90.03100,2.26400,0.03000),V(89.98500,2.41400,0.03000),V(89.97000,2.57000,0.03000),V(89.98500,2.72600,0.03000),V(90.03100,2.87600,0.03000),V(90.10500,3.01400,0.03000),V(90.20400,3.13600,0.03000),V(90.32600,3.23500,0.03000),V(90.46400,3.30900,0.03000),V(90.61400,3.35500,0.03000),V(90.77000,3.37000,0.03000),V(90.92600,3.35500,0.03000),V(91.07600,3.30900,0.03000),V(91.21400,3.23500,0.03000),V(91.33600,3.13600,0.03000),V(91.43500,3.01400,0.03000),V(91.50900,2.87600,0.03000),V(91.55500,2.72600,0.03000),V(91.57000,2.57000,0.03000),V(91.55500,2.41400,0.03000),V(91.50900,2.26400,0.03000),V(91.43500,2.12600,0.03000),V(91.33600,2.00400,0.03000),V(91.21400,1.90500,0.03000),V(91.07600,1.83100,0.03000),V(90.92600,1.78500,0.03000),V(90.77000,1.77000,0.03000)])]).extrude(V(0,0,0.01000)))
_s.append(Part.Face([_poly([V(93.31000,1.77000,0.03000),V(93.15400,1.78500,0.03000),V(93.00400,1.83100,0.03000),V(92.86600,1.90500,0.03000),V(92.74400,2.00400,0.03000),V(92.64500,2.12600,0.03000),V(92.57100,2.26400,0.03000),V(92.52500,2.41400,0.03000),V(92.51000,2.57000,0.03000),V(92.52500,2.72600,0.03000),V(92.57100,2.87600,0.03000),V(92.64500,3.01400,0.03000),V(92.74400,3.13600,0.03000),V(92.86600,3.23500,0.03000),V(93.00400,3.30900,0.03000),V(93.15400,3.35500,0.03000),V(93.31000,3.37000,0.03000),V(93.46600,3.35500,0.03000),V(93.61600,3.30900,0.03000),V(93.75400,3.23500,0.03000),V(93.87600,3.13600,0.03000),V(93.97500,3.01400,0.03000),V(94.04900,2.87600,0.03000),V(94.09500,2.72600,0.03000),V(94.11000,2.57000,0.03000),V(94.09500,2.41400,0.03000),V(94.04900,2.26400,0.03000),V(93.97500,2.12600,0.03000),V(93.87600,2.00400,0.03000),V(93.75400,1.90500,0.03000),V(93.61600,1.83100,0.03000),V(93.46600,1.78500,0.03000),V(93.31000,1.77000,0.03000)])]).extrude(V(0,0,0.01000)))
_s.append(Part.Face([_poly([V(71.30600,24.64500,0.03000),V(71.15000,24.63000,0.03000),V(70.99400,24.64500,0.03000),V(70.84400,24.69100,0.03000),V(70.70600,24.76500,0.03000),V(70.58400,24.86400,0.03000),V(70.48500,24.98600,0.03000),V(70.41100,25.12400,0.03000),V(70.36500,25.27400,0.03000),V(70.35000,25.43000,0.03000),V(70.36500,25.58600,0.03000),V(70.41100,25.73600,0.03000),V(70.48500,25.87400,0.03000),V(70.58400,25.99600,0.03000),V(70.70600,26.09500,0.03000),V(70.84400,26.16900,0.03000),V(70.99400,26.21500,0.03000),V(71.15000,26.23000,0.03000),V(71.30600,26.21500,0.03000),V(71.45600,26.16900,0.03000),V(71.59400,26.09500,0.03000),V(71.71600,25.99600,0.03000),V(71.81500,25.87400,0.03000),V(71.88900,25.73600,0.03000),V(71.93500,25.58600,0.03000),V(71.95000,25.43000,0.03000),V(71.93500,25.27400,0.03000),V(71.88900,25.12400,0.03000),V(71.81500,24.98600,0.03000),V(71.71600,24.86400,0.03000),V(71.59400,24.76500,0.03000),V(71.45600,24.69100,0.03000),V(71.30600,24.64500,0.03000)])]).extrude(V(0,0,0.01000)))
_s.append(Part.Face([_poly([V(73.69000,24.63000,0.03000),V(73.53400,24.64500,0.03000),V(73.38400,24.69100,0.03000),V(73.24600,24.76500,0.03000),V(73.12400,24.86400,0.03000),V(73.02500,24.98600,0.03000),V(72.95100,25.12400,0.03000),V(72.90500,25.27400,0.03000),V(72.89000,25.43000,0.03000),V(72.90500,25.58600,0.03000),V(72.95100,25.73600,0.03000),V(73.02500,25.87400,0.03000),V(73.12400,25.99600,0.03000),V(73.24600,26.09500,0.03000),V(73.38400,26.16900,0.03000),V(73.53400,26.21500,0.03000),V(73.69000,26.23000,0.03000),V(73.84600,26.21500,0.03000),V(73.99600,26.16900,0.03000),V(74.13400,26.09500,0.03000),V(74.25600,25.99600,0.03000),V(74.35500,25.87400,0.03000),V(74.42900,25.73600,0.03000),V(74.47500,25.58600,0.03000),V(74.49000,25.43000,0.03000),V(74.47500,25.27400,0.03000),V(74.42900,25.12400,0.03000),V(74.35500,24.98600,0.03000),V(74.25600,24.86400,0.03000),V(74.13400,24.76500,0.03000),V(73.99600,24.69100,0.03000),V(73.84600,24.64500,0.03000),V(73.69000,24.63000,0.03000)])]).extrude(V(0,0,0.01000)))
_s.append(Part.Face([_poly([V(61.14600,24.64500,0.03000),V(60.99000,24.63000,0.03000),V(60.83400,24.64500,0.03000),V(60.68400,24.69100,0.03000),V(60.54600,24.76500,0.03000),V(60.42400,24.86400,0.03000),V(60.32500,24.98600,0.03000),V(60.25100,25.12400,0.03000),V(60.20500,25.27400,0.03000),V(60.19000,25.43000,0.03000),V(60.20500,25.58600,0.03000),V(60.25100,25.73600,0.03000),V(60.32500,25.87400,0.03000),V(60.42400,25.99600,0.03000),V(60.54600,26.09500,0.03000),V(60.68400,26.16900,0.03000),V(60.83400,26.21500,0.03000),V(60.99000,26.23000,0.03000),V(61.14600,26.21500,0.03000),V(61.29600,26.16900,0.03000),V(61.43400,26.09500,0.03000),V(61.55600,25.99600,0.03000),V(61.65500,25.87400,0.03000),V(61.72900,25.73600,0.03000),V(61.77500,25.58600,0.03000),V(61.79000,25.43000,0.03000),V(61.77500,25.27400,0.03000),V(61.72900,25.12400,0.03000),V(61.65500,24.98600,0.03000),V(61.55600,24.86400,0.03000),V(61.43400,24.76500,0.03000),V(61.29600,24.69100,0.03000),V(61.14600,24.64500,0.03000)])]).extrude(V(0,0,0.01000)))
_s.append(Part.Face([_poly([V(76.23000,24.63000,0.03000),V(76.07400,24.64500,0.03000),V(75.92400,24.69100,0.03000),V(75.78600,24.76500,0.03000),V(75.66400,24.86400,0.03000),V(75.56500,24.98600,0.03000),V(75.49100,25.12400,0.03000),V(75.44500,25.27400,0.03000),V(75.43000,25.43000,0.03000),V(75.44500,25.58600,0.03000),V(75.49100,25.73600,0.03000),V(75.56500,25.87400,0.03000),V(75.66400,25.99600,0.03000),V(75.78600,26.09500,0.03000),V(75.92400,26.16900,0.03000),V(76.07400,26.21500,0.03000),V(76.23000,26.23000,0.03000),V(76.38600,26.21500,0.03000),V(76.53600,26.16900,0.03000),V(76.67400,26.09500,0.03000),V(76.79600,25.99600,0.03000),V(76.89500,25.87400,0.03000),V(76.96900,25.73600,0.03000),V(77.01500,25.58600,0.03000),V(77.03000,25.43000,0.03000),V(77.01500,25.27400,0.03000),V(76.96900,25.12400,0.03000),V(76.89500,24.98600,0.03000),V(76.79600,24.86400,0.03000),V(76.67400,24.76500,0.03000),V(76.53600,24.69100,0.03000),V(76.38600,24.64500,0.03000),V(76.23000,24.63000,0.03000)])]).extrude(V(0,0,0.01000)))
_s.append(Part.Face([_poly([V(63.68600,24.64500,0.03000),V(63.53000,24.63000,0.03000),V(63.37400,24.64500,0.03000),V(63.22400,24.69100,0.03000),V(63.08600,24.76500,0.03000),V(62.96400,24.86400,0.03000),V(62.86500,24.98600,0.03000),V(62.79100,25.12400,0.03000),V(62.74500,25.27400,0.03000),V(62.73000,25.43000,0.03000),V(62.74500,25.58600,0.03000),V(62.79100,25.73600,0.03000),V(62.86500,25.87400,0.03000),V(62.96400,25.99600,0.03000),V(63.08600,26.09500,0.03000),V(63.22400,26.16900,0.03000),V(63.37400,26.21500,0.03000),V(63.53000,26.23000,0.03000),V(63.68600,26.21500,0.03000),V(63.83600,26.16900,0.03000),V(63.97400,26.09500,0.03000),V(64.09600,25.99600,0.03000),V(64.19500,25.87400,0.03000),V(64.26900,25.73600,0.03000),V(64.31500,25.58600,0.03000),V(64.33000,25.43000,0.03000),V(64.31500,25.27400,0.03000),V(64.26900,25.12400,0.03000),V(64.19500,24.98600,0.03000),V(64.09600,24.86400,0.03000),V(63.97400,24.76500,0.03000),V(63.83600,24.69100,0.03000),V(63.68600,24.64500,0.03000)])]).extrude(V(0,0,0.01000)))
_s.append(Part.Face([_poly([V(66.22600,24.64500,0.03000),V(66.07000,24.63000,0.03000),V(65.91400,24.64500,0.03000),V(65.76400,24.69100,0.03000),V(65.62600,24.76500,0.03000),V(65.50400,24.86400,0.03000),V(65.40500,24.98600,0.03000),V(65.33100,25.12400,0.03000),V(65.28500,25.27400,0.03000),V(65.27000,25.43000,0.03000),V(65.28500,25.58600,0.03000),V(65.33100,25.73600,0.03000),V(65.40500,25.87400,0.03000),V(65.50400,25.99600,0.03000),V(65.62600,26.09500,0.03000),V(65.76400,26.16900,0.03000),V(65.91400,26.21500,0.03000),V(66.07000,26.23000,0.03000),V(66.22600,26.21500,0.03000),V(66.37600,26.16900,0.03000),V(66.51400,26.09500,0.03000),V(66.63600,25.99600,0.03000),V(66.73500,25.87400,0.03000),V(66.80900,25.73600,0.03000),V(66.85500,25.58600,0.03000),V(66.87000,25.43000,0.03000),V(66.85500,25.27400,0.03000),V(66.80900,25.12400,0.03000),V(66.73500,24.98600,0.03000),V(66.63600,24.86400,0.03000),V(66.51400,24.76500,0.03000),V(66.37600,24.69100,0.03000),V(66.22600,24.64500,0.03000)])]).extrude(V(0,0,0.01000)))
_s.append(Part.Face([_poly([V(90.92600,24.64500,0.03000),V(90.77000,24.63000,0.03000),V(90.61400,24.64500,0.03000),V(90.46400,24.69100,0.03000),V(90.32600,24.76500,0.03000),V(90.20400,24.86400,0.03000),V(90.10500,24.98600,0.03000),V(90.03100,25.12400,0.03000),V(89.98500,25.27400,0.03000),V(89.97000,25.43000,0.03000),V(89.98500,25.58600,0.03000),V(90.03100,25.73600,0.03000),V(90.10500,25.87400,0.03000),V(90.20400,25.99600,0.03000),V(90.32600,26.09500,0.03000),V(90.46400,26.16900,0.03000),V(90.61400,26.21500,0.03000),V(90.77000,26.23000,0.03000),V(90.92600,26.21500,0.03000),V(91.07600,26.16900,0.03000),V(91.21400,26.09500,0.03000),V(91.33600,25.99600,0.03000),V(91.43500,25.87400,0.03000),V(91.50900,25.73600,0.03000),V(91.55500,25.58600,0.03000),V(91.57000,25.43000,0.03000),V(91.55500,25.27400,0.03000),V(91.50900,25.12400,0.03000),V(91.43500,24.98600,0.03000),V(91.33600,24.86400,0.03000),V(91.21400,24.76500,0.03000),V(91.07600,24.69100,0.03000),V(90.92600,24.64500,0.03000)])]).extrude(V(0,0,0.01000)))
_s.append(Part.Face([_poly([V(68.61000,24.63000,0.03000),V(68.45400,24.64500,0.03000),V(68.30400,24.69100,0.03000),V(68.16600,24.76500,0.03000),V(68.04400,24.86400,0.03000),V(67.94500,24.98600,0.03000),V(67.87100,25.12400,0.03000),V(67.82500,25.27400,0.03000),V(67.81000,25.43000,0.03000),V(67.82500,25.58600,0.03000),V(67.87100,25.73600,0.03000),V(67.94500,25.87400,0.03000),V(68.04400,25.99600,0.03000),V(68.16600,26.09500,0.03000),V(68.30400,26.16900,0.03000),V(68.45400,26.21500,0.03000),V(68.61000,26.23000,0.03000),V(68.76600,26.21500,0.03000),V(68.91600,26.16900,0.03000),V(69.05400,26.09500,0.03000),V(69.17600,25.99600,0.03000),V(69.27500,25.87400,0.03000),V(69.34900,25.73600,0.03000),V(69.39500,25.58600,0.03000),V(69.41000,25.43000,0.03000),V(69.39500,25.27400,0.03000),V(69.34900,25.12400,0.03000),V(69.27500,24.98600,0.03000),V(69.17600,24.86400,0.03000),V(69.05400,24.76500,0.03000),V(68.91600,24.69100,0.03000),V(68.76600,24.64500,0.03000),V(68.61000,24.63000,0.03000)])]).extrude(V(0,0,0.01000)))
_s.append(Part.Face([_poly([V(93.46600,24.64500,0.03000),V(93.31000,24.63000,0.03000),V(93.15400,24.64500,0.03000),V(93.00400,24.69100,0.03000),V(92.86600,24.76500,0.03000),V(92.74400,24.86400,0.03000),V(92.64500,24.98600,0.03000),V(92.57100,25.12400,0.03000),V(92.52500,25.27400,0.03000),V(92.51000,25.43000,0.03000),V(92.52500,25.58600,0.03000),V(92.57100,25.73600,0.03000),V(92.64500,25.87400,0.03000),V(92.74400,25.99600,0.03000),V(92.86600,26.09500,0.03000),V(93.00400,26.16900,0.03000),V(93.15400,26.21500,0.03000),V(93.31000,26.23000,0.03000),V(93.46600,26.21500,0.03000),V(93.61600,26.16900,0.03000),V(93.75400,26.09500,0.03000),V(93.87600,25.99600,0.03000),V(93.97500,25.87400,0.03000),V(94.04900,25.73600,0.03000),V(94.09500,25.58600,0.03000),V(94.11000,25.43000,0.03000),V(94.09500,25.27400,0.03000),V(94.04900,25.12400,0.03000),V(93.97500,24.98600,0.03000),V(93.87600,24.86400,0.03000),V(93.75400,24.76500,0.03000),V(93.61600,24.69100,0.03000),V(93.46600,24.64500,0.03000)])]).extrude(V(0,0,0.01000)))
_s.append(Part.Face([_poly([V(95.85000,1.77000,0.03000),V(95.69400,1.78500,0.03000),V(95.54400,1.83100,0.03000),V(95.40600,1.90500,0.03000),V(95.28400,2.00400,0.03000),V(95.18500,2.12600,0.03000),V(95.11100,2.26400,0.03000),V(95.06500,2.41400,0.03000),V(95.05000,2.57000,0.03000),V(95.06500,2.72600,0.03000),V(95.11100,2.87600,0.03000),V(95.18500,3.01400,0.03000),V(95.28400,3.13600,0.03000),V(95.40600,3.23500,0.03000),V(95.54400,3.30900,0.03000),V(95.69400,3.35500,0.03000),V(95.85000,3.37000,0.03000),V(96.00600,3.35500,0.03000),V(96.15600,3.30900,0.03000),V(96.29400,3.23500,0.03000),V(96.41600,3.13600,0.03000),V(96.51500,3.01400,0.03000),V(96.58900,2.87600,0.03000),V(96.63500,2.72600,0.03000),V(96.65000,2.57000,0.03000),V(96.63500,2.41400,0.03000),V(96.58900,2.26400,0.03000),V(96.51500,2.12600,0.03000),V(96.41600,2.00400,0.03000),V(96.29400,1.90500,0.03000),V(96.15600,1.83100,0.03000),V(96.00600,1.78500,0.03000),V(95.85000,1.77000,0.03000)])]).extrude(V(0,0,0.01000)))
_s.append(Part.Face([_poly([V(108.55000,1.77000,0.03000),V(108.39400,1.78500,0.03000),V(108.24400,1.83100,0.03000),V(108.10600,1.90500,0.03000),V(107.98400,2.00400,0.03000),V(107.88500,2.12600,0.03000),V(107.81100,2.26400,0.03000),V(107.76500,2.41400,0.03000),V(107.75000,2.57000,0.03000),V(107.76500,2.72600,0.03000),V(107.81100,2.87600,0.03000),V(107.88500,3.01400,0.03000),V(107.98400,3.13600,0.03000),V(108.10600,3.23500,0.03000),V(108.24400,3.30900,0.03000),V(108.39400,3.35500,0.03000),V(108.55000,3.37000,0.03000),V(108.70600,3.35500,0.03000),V(108.85600,3.30900,0.03000),V(108.99400,3.23500,0.03000),V(109.11600,3.13600,0.03000),V(109.21500,3.01400,0.03000),V(109.28900,2.87600,0.03000),V(109.33500,2.72600,0.03000),V(109.35000,2.57000,0.03000),V(109.33500,2.41400,0.03000),V(109.28900,2.26400,0.03000),V(109.21500,2.12600,0.03000),V(109.11600,2.00400,0.03000),V(108.99400,1.90500,0.03000),V(108.85600,1.83100,0.03000),V(108.70600,1.78500,0.03000),V(108.55000,1.77000,0.03000)])]).extrude(V(0,0,0.01000)))
_s.append(Part.Face([_poly([V(98.54600,1.78500,0.03000),V(98.39000,1.77000,0.03000),V(98.23400,1.78500,0.03000),V(98.08400,1.83100,0.03000),V(97.94600,1.90500,0.03000),V(97.82400,2.00400,0.03000),V(97.72500,2.12600,0.03000),V(97.65100,2.26400,0.03000),V(97.60500,2.41400,0.03000),V(97.59000,2.57000,0.03000),V(97.60500,2.72600,0.03000),V(97.65100,2.87600,0.03000),V(97.72500,3.01400,0.03000),V(97.82400,3.13600,0.03000),V(97.94600,3.23500,0.03000),V(98.08400,3.30900,0.03000),V(98.23400,3.35500,0.03000),V(98.39000,3.37000,0.03000),V(98.54600,3.35500,0.03000),V(98.69600,3.30900,0.03000),V(98.83400,3.23500,0.03000),V(98.95600,3.13600,0.03000),V(99.05500,3.01400,0.03000),V(99.12900,2.87600,0.03000),V(99.17500,2.72600,0.03000),V(99.19000,2.57000,0.03000),V(99.17500,2.41400,0.03000),V(99.12900,2.26400,0.03000),V(99.05500,2.12600,0.03000),V(98.95600,2.00400,0.03000),V(98.83400,1.90500,0.03000),V(98.69600,1.83100,0.03000),V(98.54600,1.78500,0.03000)])]).extrude(V(0,0,0.01000)))
_s.append(Part.Face([_poly([V(111.09000,1.77000,0.03000),V(110.93400,1.78500,0.03000),V(110.78400,1.83100,0.03000),V(110.64600,1.90500,0.03000),V(110.52400,2.00400,0.03000),V(110.42500,2.12600,0.03000),V(110.35100,2.26400,0.03000),V(110.30500,2.41400,0.03000),V(110.29000,2.57000,0.03000),V(110.30500,2.72600,0.03000),V(110.35100,2.87600,0.03000),V(110.42500,3.01400,0.03000),V(110.52400,3.13600,0.03000),V(110.64600,3.23500,0.03000),V(110.78400,3.30900,0.03000),V(110.93400,3.35500,0.03000),V(111.09000,3.37000,0.03000),V(111.24600,3.35500,0.03000),V(111.39600,3.30900,0.03000),V(111.53400,3.23500,0.03000),V(111.65600,3.13600,0.03000),V(111.75500,3.01400,0.03000),V(111.82900,2.87600,0.03000),V(111.87500,2.72600,0.03000),V(111.89000,2.57000,0.03000),V(111.87500,2.41400,0.03000),V(111.82900,2.26400,0.03000),V(111.75500,2.12600,0.03000),V(111.65600,2.00400,0.03000),V(111.53400,1.90500,0.03000),V(111.39600,1.83100,0.03000),V(111.24600,1.78500,0.03000),V(111.09000,1.77000,0.03000)])]).extrude(V(0,0,0.01000)))
_s.append(Part.Face([_poly([V(100.93000,1.77000,0.03000),V(100.77400,1.78500,0.03000),V(100.62400,1.83100,0.03000),V(100.48600,1.90500,0.03000),V(100.36400,2.00400,0.03000),V(100.26500,2.12600,0.03000),V(100.19100,2.26400,0.03000),V(100.14500,2.41400,0.03000),V(100.13000,2.57000,0.03000),V(100.14500,2.72600,0.03000),V(100.19100,2.87600,0.03000),V(100.26500,3.01400,0.03000),V(100.36400,3.13600,0.03000),V(100.48600,3.23500,0.03000),V(100.62400,3.30900,0.03000),V(100.77400,3.35500,0.03000),V(100.93000,3.37000,0.03000),V(101.08600,3.35500,0.03000),V(101.23600,3.30900,0.03000),V(101.37400,3.23500,0.03000),V(101.49600,3.13600,0.03000),V(101.59500,3.01400,0.03000),V(101.66900,2.87600,0.03000),V(101.71500,2.72600,0.03000),V(101.73000,2.57000,0.03000),V(101.71500,2.41400,0.03000),V(101.66900,2.26400,0.03000),V(101.59500,2.12600,0.03000),V(101.49600,2.00400,0.03000),V(101.37400,1.90500,0.03000),V(101.23600,1.83100,0.03000),V(101.08600,1.78500,0.03000),V(100.93000,1.77000,0.03000)])]).extrude(V(0,0,0.01000)))
_s.append(Part.Face([_poly([V(113.63000,1.77000,0.03000),V(113.47400,1.78500,0.03000),V(113.32400,1.83100,0.03000),V(113.18600,1.90500,0.03000),V(113.06400,2.00400,0.03000),V(112.96500,2.12600,0.03000),V(112.89100,2.26400,0.03000),V(112.84500,2.41400,0.03000),V(112.83000,2.57000,0.03000),V(112.84500,2.72600,0.03000),V(112.89100,2.87600,0.03000),V(112.96500,3.01400,0.03000),V(113.06400,3.13600,0.03000),V(113.18600,3.23500,0.03000),V(113.32400,3.30900,0.03000),V(113.47400,3.35500,0.03000),V(113.63000,3.37000,0.03000),V(113.78600,3.35500,0.03000),V(113.93600,3.30900,0.03000),V(114.07400,3.23500,0.03000),V(114.19600,3.13600,0.03000),V(114.29500,3.01400,0.03000),V(114.36900,2.87600,0.03000),V(114.41500,2.72600,0.03000),V(114.43000,2.57000,0.03000),V(114.41500,2.41400,0.03000),V(114.36900,2.26400,0.03000),V(114.29500,2.12600,0.03000),V(114.19600,2.00400,0.03000),V(114.07400,1.90500,0.03000),V(113.93600,1.83100,0.03000),V(113.78600,1.78500,0.03000),V(113.63000,1.77000,0.03000)])]).extrude(V(0,0,0.01000)))
_s.append(Part.Face([_poly([V(103.62600,1.78500,0.03000),V(103.47000,1.77000,0.03000),V(103.31400,1.78500,0.03000),V(103.16400,1.83100,0.03000),V(103.02600,1.90500,0.03000),V(102.90400,2.00400,0.03000),V(102.80500,2.12600,0.03000),V(102.73100,2.26400,0.03000),V(102.68500,2.41400,0.03000),V(102.67000,2.57000,0.03000),V(102.68500,2.72600,0.03000),V(102.73100,2.87600,0.03000),V(102.80500,3.01400,0.03000),V(102.90400,3.13600,0.03000),V(103.02600,3.23500,0.03000),V(103.16400,3.30900,0.03000),V(103.31400,3.35500,0.03000),V(103.47000,3.37000,0.03000),V(103.62600,3.35500,0.03000),V(103.77600,3.30900,0.03000),V(103.91400,3.23500,0.03000),V(104.03600,3.13600,0.03000),V(104.13500,3.01400,0.03000),V(104.20900,2.87600,0.03000),V(104.25500,2.72600,0.03000),V(104.27000,2.57000,0.03000),V(104.25500,2.41400,0.03000),V(104.20900,2.26400,0.03000),V(104.13500,2.12600,0.03000),V(104.03600,2.00400,0.03000),V(103.91400,1.90500,0.03000),V(103.77600,1.83100,0.03000),V(103.62600,1.78500,0.03000)])]).extrude(V(0,0,0.01000)))
_s.append(Part.Face([_poly([V(116.32600,1.78500,0.03000),V(116.17000,1.77000,0.03000),V(116.01400,1.78500,0.03000),V(115.86400,1.83100,0.03000),V(115.72600,1.90500,0.03000),V(115.60400,2.00400,0.03000),V(115.50500,2.12600,0.03000),V(115.43100,2.26400,0.03000),V(115.38500,2.41400,0.03000),V(115.37000,2.57000,0.03000),V(115.38500,2.72600,0.03000),V(115.43100,2.87600,0.03000),V(115.50500,3.01400,0.03000),V(115.60400,3.13600,0.03000),V(115.72600,3.23500,0.03000),V(115.86400,3.30900,0.03000),V(116.01400,3.35500,0.03000),V(116.17000,3.37000,0.03000),V(116.32600,3.35500,0.03000),V(116.47600,3.30900,0.03000),V(116.61400,3.23500,0.03000),V(116.73600,3.13600,0.03000),V(116.83500,3.01400,0.03000),V(116.90900,2.87600,0.03000),V(116.95500,2.72600,0.03000),V(116.97000,2.57000,0.03000),V(116.95500,2.41400,0.03000),V(116.90900,2.26400,0.03000),V(116.83500,2.12600,0.03000),V(116.73600,2.00400,0.03000),V(116.61400,1.90500,0.03000),V(116.47600,1.83100,0.03000),V(116.32600,1.78500,0.03000)])]).extrude(V(0,0,0.01000)))
_s.append(Part.Face([_poly([V(106.01000,1.77000,0.03000),V(105.85400,1.78500,0.03000),V(105.70400,1.83100,0.03000),V(105.56600,1.90500,0.03000),V(105.44400,2.00400,0.03000),V(105.34500,2.12600,0.03000),V(105.27100,2.26400,0.03000),V(105.22500,2.41400,0.03000),V(105.21000,2.57000,0.03000),V(105.22500,2.72600,0.03000),V(105.27100,2.87600,0.03000),V(105.34500,3.01400,0.03000),V(105.44400,3.13600,0.03000),V(105.56600,3.23500,0.03000),V(105.70400,3.30900,0.03000),V(105.85400,3.35500,0.03000),V(106.01000,3.37000,0.03000),V(106.16600,3.35500,0.03000),V(106.31600,3.30900,0.03000),V(106.45400,3.23500,0.03000),V(106.57600,3.13600,0.03000),V(106.67500,3.01400,0.03000),V(106.74900,2.87600,0.03000),V(106.79500,2.72600,0.03000),V(106.81000,2.57000,0.03000),V(106.79500,2.41400,0.03000),V(106.74900,2.26400,0.03000),V(106.67500,2.12600,0.03000),V(106.57600,2.00400,0.03000),V(106.45400,1.90500,0.03000),V(106.31600,1.83100,0.03000),V(106.16600,1.78500,0.03000),V(106.01000,1.77000,0.03000)])]).extrude(V(0,0,0.01000)))
_s.append(Part.Face([_poly([V(96.00600,24.64500,0.03000),V(95.85000,24.63000,0.03000),V(95.69400,24.64500,0.03000),V(95.54400,24.69100,0.03000),V(95.40600,24.76500,0.03000),V(95.28400,24.86400,0.03000),V(95.18500,24.98600,0.03000),V(95.11100,25.12400,0.03000),V(95.06500,25.27400,0.03000),V(95.05000,25.43000,0.03000),V(95.06500,25.58600,0.03000),V(95.11100,25.73600,0.03000),V(95.18500,25.87400,0.03000),V(95.28400,25.99600,0.03000),V(95.40600,26.09500,0.03000),V(95.54400,26.16900,0.03000),V(95.69400,26.21500,0.03000),V(95.85000,26.23000,0.03000),V(96.00600,26.21500,0.03000),V(96.15600,26.16900,0.03000),V(96.29400,26.09500,0.03000),V(96.41600,25.99600,0.03000),V(96.51500,25.87400,0.03000),V(96.58900,25.73600,0.03000),V(96.63500,25.58600,0.03000),V(96.65000,25.43000,0.03000),V(96.63500,25.27400,0.03000),V(96.58900,25.12400,0.03000),V(96.51500,24.98600,0.03000),V(96.41600,24.86400,0.03000),V(96.29400,24.76500,0.03000),V(96.15600,24.69100,0.03000),V(96.00600,24.64500,0.03000)])]).extrude(V(0,0,0.01000)))
_s.append(Part.Face([_poly([V(98.54600,24.64500,0.03000),V(98.39000,24.63000,0.03000),V(98.23400,24.64500,0.03000),V(98.08400,24.69100,0.03000),V(97.94600,24.76500,0.03000),V(97.82400,24.86400,0.03000),V(97.72500,24.98600,0.03000),V(97.65100,25.12400,0.03000),V(97.60500,25.27400,0.03000),V(97.59000,25.43000,0.03000),V(97.60500,25.58600,0.03000),V(97.65100,25.73600,0.03000),V(97.72500,25.87400,0.03000),V(97.82400,25.99600,0.03000),V(97.94600,26.09500,0.03000),V(98.08400,26.16900,0.03000),V(98.23400,26.21500,0.03000),V(98.39000,26.23000,0.03000),V(98.54600,26.21500,0.03000),V(98.69600,26.16900,0.03000),V(98.83400,26.09500,0.03000),V(98.95600,25.99600,0.03000),V(99.05500,25.87400,0.03000),V(99.12900,25.73600,0.03000),V(99.17500,25.58600,0.03000),V(99.19000,25.43000,0.03000),V(99.17500,25.27400,0.03000),V(99.12900,25.12400,0.03000),V(99.05500,24.98600,0.03000),V(98.95600,24.86400,0.03000),V(98.83400,24.76500,0.03000),V(98.69600,24.69100,0.03000),V(98.54600,24.64500,0.03000)])]).extrude(V(0,0,0.01000)))
_s.append(Part.Face([_poly([V(100.93000,24.63000,0.03000),V(100.77400,24.64500,0.03000),V(100.62400,24.69100,0.03000),V(100.48600,24.76500,0.03000),V(100.36400,24.86400,0.03000),V(100.26500,24.98600,0.03000),V(100.19100,25.12400,0.03000),V(100.14500,25.27400,0.03000),V(100.13000,25.43000,0.03000),V(100.14500,25.58600,0.03000),V(100.19100,25.73600,0.03000),V(100.26500,25.87400,0.03000),V(100.36400,25.99600,0.03000),V(100.48600,26.09500,0.03000),V(100.62400,26.16900,0.03000),V(100.77400,26.21500,0.03000),V(100.93000,26.23000,0.03000),V(101.08600,26.21500,0.03000),V(101.23600,26.16900,0.03000),V(101.37400,26.09500,0.03000),V(101.49600,25.99600,0.03000),V(101.59500,25.87400,0.03000),V(101.66900,25.73600,0.03000),V(101.71500,25.58600,0.03000),V(101.73000,25.43000,0.03000),V(101.71500,25.27400,0.03000),V(101.66900,25.12400,0.03000),V(101.59500,24.98600,0.03000),V(101.49600,24.86400,0.03000),V(101.37400,24.76500,0.03000),V(101.23600,24.69100,0.03000),V(101.08600,24.64500,0.03000),V(100.93000,24.63000,0.03000)])]).extrude(V(0,0,0.01000)))
_s.append(Part.Face([_poly([V(103.62600,24.64500,0.03000),V(103.47000,24.63000,0.03000),V(103.31400,24.64500,0.03000),V(103.16400,24.69100,0.03000),V(103.02600,24.76500,0.03000),V(102.90400,24.86400,0.03000),V(102.80500,24.98600,0.03000),V(102.73100,25.12400,0.03000),V(102.68500,25.27400,0.03000),V(102.67000,25.43000,0.03000),V(102.68500,25.58600,0.03000),V(102.73100,25.73600,0.03000),V(102.80500,25.87400,0.03000),V(102.90400,25.99600,0.03000),V(103.02600,26.09500,0.03000),V(103.16400,26.16900,0.03000),V(103.31400,26.21500,0.03000),V(103.47000,26.23000,0.03000),V(103.62600,26.21500,0.03000),V(103.77600,26.16900,0.03000),V(103.91400,26.09500,0.03000),V(104.03600,25.99600,0.03000),V(104.13500,25.87400,0.03000),V(104.20900,25.73600,0.03000),V(104.25500,25.58600,0.03000),V(104.27000,25.43000,0.03000),V(104.25500,25.27400,0.03000),V(104.20900,25.12400,0.03000),V(104.13500,24.98600,0.03000),V(104.03600,24.86400,0.03000),V(103.91400,24.76500,0.03000),V(103.77600,24.69100,0.03000),V(103.62600,24.64500,0.03000)])]).extrude(V(0,0,0.01000)))
_s.append(Part.Face([_poly([V(111.24600,24.64500,0.03000),V(111.09000,24.63000,0.03000),V(110.93400,24.64500,0.03000),V(110.78400,24.69100,0.03000),V(110.64600,24.76500,0.03000),V(110.52400,24.86400,0.03000),V(110.42500,24.98600,0.03000),V(110.35100,25.12400,0.03000),V(110.30500,25.27400,0.03000),V(110.29000,25.43000,0.03000),V(110.30500,25.58600,0.03000),V(110.35100,25.73600,0.03000),V(110.42500,25.87400,0.03000),V(110.52400,25.99600,0.03000),V(110.64600,26.09500,0.03000),V(110.78400,26.16900,0.03000),V(110.93400,26.21500,0.03000),V(111.09000,26.23000,0.03000),V(111.24600,26.21500,0.03000),V(111.39600,26.16900,0.03000),V(111.53400,26.09500,0.03000),V(111.65600,25.99600,0.03000),V(111.75500,25.87400,0.03000),V(111.82900,25.73600,0.03000),V(111.87500,25.58600,0.03000),V(111.89000,25.43000,0.03000),V(111.87500,25.27400,0.03000),V(111.82900,25.12400,0.03000),V(111.75500,24.98600,0.03000),V(111.65600,24.86400,0.03000),V(111.53400,24.76500,0.03000),V(111.39600,24.69100,0.03000),V(111.24600,24.64500,0.03000)])]).extrude(V(0,0,0.01000)))
_s.append(Part.Face([_poly([V(108.70600,24.64500,0.03000),V(108.55000,24.63000,0.03000),V(108.39400,24.64500,0.03000),V(108.24400,24.69100,0.03000),V(108.10600,24.76500,0.03000),V(107.98400,24.86400,0.03000),V(107.88500,24.98600,0.03000),V(107.81100,25.12400,0.03000),V(107.76500,25.27400,0.03000),V(107.75000,25.43000,0.03000),V(107.76500,25.58600,0.03000),V(107.81100,25.73600,0.03000),V(107.88500,25.87400,0.03000),V(107.98400,25.99600,0.03000),V(108.10600,26.09500,0.03000),V(108.24400,26.16900,0.03000),V(108.39400,26.21500,0.03000),V(108.55000,26.23000,0.03000),V(108.70600,26.21500,0.03000),V(108.85600,26.16900,0.03000),V(108.99400,26.09500,0.03000),V(109.11600,25.99600,0.03000),V(109.21500,25.87400,0.03000),V(109.28900,25.73600,0.03000),V(109.33500,25.58600,0.03000),V(109.35000,25.43000,0.03000),V(109.33500,25.27400,0.03000),V(109.28900,25.12400,0.03000),V(109.21500,24.98600,0.03000),V(109.11600,24.86400,0.03000),V(108.99400,24.76500,0.03000),V(108.85600,24.69100,0.03000),V(108.70600,24.64500,0.03000)])]).extrude(V(0,0,0.01000)))
_s.append(Part.Face([_poly([V(106.16600,24.64500,0.03000),V(106.01000,24.63000,0.03000),V(105.85400,24.64500,0.03000),V(105.70400,24.69100,0.03000),V(105.56600,24.76500,0.03000),V(105.44400,24.86400,0.03000),V(105.34500,24.98600,0.03000),V(105.27100,25.12400,0.03000),V(105.22500,25.27400,0.03000),V(105.21000,25.43000,0.03000),V(105.22500,25.58600,0.03000),V(105.27100,25.73600,0.03000),V(105.34500,25.87400,0.03000),V(105.44400,25.99600,0.03000),V(105.56600,26.09500,0.03000),V(105.70400,26.16900,0.03000),V(105.85400,26.21500,0.03000),V(106.01000,26.23000,0.03000),V(106.16600,26.21500,0.03000),V(106.31600,26.16900,0.03000),V(106.45400,26.09500,0.03000),V(106.57600,25.99600,0.03000),V(106.67500,25.87400,0.03000),V(106.74900,25.73600,0.03000),V(106.79500,25.58600,0.03000),V(106.81000,25.43000,0.03000),V(106.79500,25.27400,0.03000),V(106.74900,25.12400,0.03000),V(106.67500,24.98600,0.03000),V(106.57600,24.86400,0.03000),V(106.45400,24.76500,0.03000),V(106.31600,24.69100,0.03000),V(106.16600,24.64500,0.03000)])]).extrude(V(0,0,0.01000)))
_s.append(Part.Face([_poly([V(113.63000,24.63000,0.03000),V(113.47400,24.64500,0.03000),V(113.32400,24.69100,0.03000),V(113.18600,24.76500,0.03000),V(113.06400,24.86400,0.03000),V(112.96500,24.98600,0.03000),V(112.89100,25.12400,0.03000),V(112.84500,25.27400,0.03000),V(112.83000,25.43000,0.03000),V(112.84500,25.58600,0.03000),V(112.89100,25.73600,0.03000),V(112.96500,25.87400,0.03000),V(113.06400,25.99600,0.03000),V(113.18600,26.09500,0.03000),V(113.32400,26.16900,0.03000),V(113.47400,26.21500,0.03000),V(113.63000,26.23000,0.03000),V(113.78600,26.21500,0.03000),V(113.93600,26.16900,0.03000),V(114.07400,26.09500,0.03000),V(114.19600,25.99600,0.03000),V(114.29500,25.87400,0.03000),V(114.36900,25.73600,0.03000),V(114.41500,25.58600,0.03000),V(114.43000,25.43000,0.03000),V(114.41500,25.27400,0.03000),V(114.36900,25.12400,0.03000),V(114.29500,24.98600,0.03000),V(114.19600,24.86400,0.03000),V(114.07400,24.76500,0.03000),V(113.93600,24.69100,0.03000),V(113.78600,24.64500,0.03000),V(113.63000,24.63000,0.03000)])]).extrude(V(0,0,0.01000)))
_s.append(Part.Face([_poly([V(116.17000,24.63000,0.03000),V(116.01400,24.64500,0.03000),V(115.86400,24.69100,0.03000),V(115.72600,24.76500,0.03000),V(115.60400,24.86400,0.03000),V(115.50500,24.98600,0.03000),V(115.43100,25.12400,0.03000),V(115.38500,25.27400,0.03000),V(115.37000,25.43000,0.03000),V(115.38500,25.58600,0.03000),V(115.43100,25.73600,0.03000),V(115.50500,25.87400,0.03000),V(115.60400,25.99600,0.03000),V(115.72600,26.09500,0.03000),V(115.86400,26.16900,0.03000),V(116.01400,26.21500,0.03000),V(116.17000,26.23000,0.03000),V(116.32600,26.21500,0.03000),V(116.47600,26.16900,0.03000),V(116.61400,26.09500,0.03000),V(116.73600,25.99600,0.03000),V(116.83500,25.87400,0.03000),V(116.90900,25.73600,0.03000),V(116.95500,25.58600,0.03000),V(116.97000,25.43000,0.03000),V(116.95500,25.27400,0.03000),V(116.90900,25.12400,0.03000),V(116.83500,24.98600,0.03000),V(116.73600,24.86400,0.03000),V(116.61400,24.76500,0.03000),V(116.47600,24.69100,0.03000),V(116.32600,24.64500,0.03000),V(116.17000,24.63000,0.03000)])]).extrude(V(0,0,0.01000)))
_s.append(Part.Face([_poly([V(118.86600,1.78500,0.03000),V(118.71000,1.77000,0.03000),V(118.55400,1.78500,0.03000),V(118.40400,1.83100,0.03000),V(118.26600,1.90500,0.03000),V(118.14400,2.00400,0.03000),V(118.04500,2.12600,0.03000),V(117.97100,2.26400,0.03000),V(117.92500,2.41400,0.03000),V(117.91000,2.57000,0.03000),V(117.92500,2.72600,0.03000),V(117.97100,2.87600,0.03000),V(118.04500,3.01400,0.03000),V(118.14400,3.13600,0.03000),V(118.26600,3.23500,0.03000),V(118.40400,3.30900,0.03000),V(118.55400,3.35500,0.03000),V(118.71000,3.37000,0.03000),V(118.86600,3.35500,0.03000),V(119.01600,3.30900,0.03000),V(119.15400,3.23500,0.03000),V(119.27600,3.13600,0.03000),V(119.37500,3.01400,0.03000),V(119.44900,2.87600,0.03000),V(119.49500,2.72600,0.03000),V(119.51000,2.57000,0.03000),V(119.49500,2.41400,0.03000),V(119.44900,2.26400,0.03000),V(119.37500,2.12600,0.03000),V(119.27600,2.00400,0.03000),V(119.15400,1.90500,0.03000),V(119.01600,1.83100,0.03000),V(118.86600,1.78500,0.03000)])]).extrude(V(0,0,0.01000)))
_s.append(Part.Face([_poly([V(129.02600,1.78500,0.03000),V(128.87000,1.77000,0.03000),V(128.71400,1.78500,0.03000),V(128.56400,1.83100,0.03000),V(128.42600,1.90500,0.03000),V(128.30400,2.00400,0.03000),V(128.20500,2.12600,0.03000),V(128.13100,2.26400,0.03000),V(128.08500,2.41400,0.03000),V(128.07000,2.57000,0.03000),V(128.08500,2.72600,0.03000),V(128.13100,2.87600,0.03000),V(128.20500,3.01400,0.03000),V(128.30400,3.13600,0.03000),V(128.42600,3.23500,0.03000),V(128.56400,3.30900,0.03000),V(128.71400,3.35500,0.03000),V(128.87000,3.37000,0.03000),V(129.02600,3.35500,0.03000),V(129.17600,3.30900,0.03000),V(129.31400,3.23500,0.03000),V(129.43600,3.13600,0.03000),V(129.53500,3.01400,0.03000),V(129.60900,2.87600,0.03000),V(129.65500,2.72600,0.03000),V(129.67000,2.57000,0.03000),V(129.65500,2.41400,0.03000),V(129.60900,2.26400,0.03000),V(129.53500,2.12600,0.03000),V(129.43600,2.00400,0.03000),V(129.31400,1.90500,0.03000),V(129.17600,1.83100,0.03000),V(129.02600,1.78500,0.03000)])]).extrude(V(0,0,0.01000)))
_s.append(Part.Face([_poly([V(131.41000,1.77000,0.03000),V(131.25400,1.78500,0.03000),V(131.10400,1.83100,0.03000),V(130.96600,1.90500,0.03000),V(130.84400,2.00400,0.03000),V(130.74500,2.12600,0.03000),V(130.67100,2.26400,0.03000),V(130.62500,2.41400,0.03000),V(130.61000,2.57000,0.03000),V(130.62500,2.72600,0.03000),V(130.67100,2.87600,0.03000),V(130.74500,3.01400,0.03000),V(130.84400,3.13600,0.03000),V(130.96600,3.23500,0.03000),V(131.10400,3.30900,0.03000),V(131.25400,3.35500,0.03000),V(131.41000,3.37000,0.03000),V(131.56600,3.35500,0.03000),V(131.71600,3.30900,0.03000),V(131.85400,3.23500,0.03000),V(131.97600,3.13600,0.03000),V(132.07500,3.01400,0.03000),V(132.14900,2.87600,0.03000),V(132.19500,2.72600,0.03000),V(132.21000,2.57000,0.03000),V(132.19500,2.41400,0.03000),V(132.14900,2.26400,0.03000),V(132.07500,2.12600,0.03000),V(131.97600,2.00400,0.03000),V(131.85400,1.90500,0.03000),V(131.71600,1.83100,0.03000),V(131.56600,1.78500,0.03000),V(131.41000,1.77000,0.03000)])]).extrude(V(0,0,0.01000)))
_s.append(Part.Face([_poly([V(121.40600,1.78500,0.03000),V(121.25000,1.77000,0.03000),V(121.09400,1.78500,0.03000),V(120.94400,1.83100,0.03000),V(120.80600,1.90500,0.03000),V(120.68400,2.00400,0.03000),V(120.58500,2.12600,0.03000),V(120.51100,2.26400,0.03000),V(120.46500,2.41400,0.03000),V(120.45000,2.57000,0.03000),V(120.46500,2.72600,0.03000),V(120.51100,2.87600,0.03000),V(120.58500,3.01400,0.03000),V(120.68400,3.13600,0.03000),V(120.80600,3.23500,0.03000),V(120.94400,3.30900,0.03000),V(121.09400,3.35500,0.03000),V(121.25000,3.37000,0.03000),V(121.40600,3.35500,0.03000),V(121.55600,3.30900,0.03000),V(121.69400,3.23500,0.03000),V(121.81600,3.13600,0.03000),V(121.91500,3.01400,0.03000),V(121.98900,2.87600,0.03000),V(122.03500,2.72600,0.03000),V(122.05000,2.57000,0.03000),V(122.03500,2.41400,0.03000),V(121.98900,2.26400,0.03000),V(121.91500,2.12600,0.03000),V(121.81600,2.00400,0.03000),V(121.69400,1.90500,0.03000),V(121.55600,1.83100,0.03000),V(121.40600,1.78500,0.03000)])]).extrude(V(0,0,0.01000)))
_s.append(Part.Face([_poly([V(123.79000,1.77000,0.03000),V(123.63400,1.78500,0.03000),V(123.48400,1.83100,0.03000),V(123.34600,1.90500,0.03000),V(123.22400,2.00400,0.03000),V(123.12500,2.12600,0.03000),V(123.05100,2.26400,0.03000),V(123.00500,2.41400,0.03000),V(122.99000,2.57000,0.03000),V(123.00500,2.72600,0.03000),V(123.05100,2.87600,0.03000),V(123.12500,3.01400,0.03000),V(123.22400,3.13600,0.03000),V(123.34600,3.23500,0.03000),V(123.48400,3.30900,0.03000),V(123.63400,3.35500,0.03000),V(123.79000,3.37000,0.03000),V(123.94600,3.35500,0.03000),V(124.09600,3.30900,0.03000),V(124.23400,3.23500,0.03000),V(124.35600,3.13600,0.03000),V(124.45500,3.01400,0.03000),V(124.52900,2.87600,0.03000),V(124.57500,2.72600,0.03000),V(124.59000,2.57000,0.03000),V(124.57500,2.41400,0.03000),V(124.52900,2.26400,0.03000),V(124.45500,2.12600,0.03000),V(124.35600,2.00400,0.03000),V(124.23400,1.90500,0.03000),V(124.09600,1.83100,0.03000),V(123.94600,1.78500,0.03000),V(123.79000,1.77000,0.03000)])]).extrude(V(0,0,0.01000)))
_s.append(Part.Face([_poly([V(134.10600,1.78500,0.03000),V(133.95000,1.77000,0.03000),V(133.79400,1.78500,0.03000),V(133.64400,1.83100,0.03000),V(133.50600,1.90500,0.03000),V(133.38400,2.00400,0.03000),V(133.28500,2.12600,0.03000),V(133.21100,2.26400,0.03000),V(133.16500,2.41400,0.03000),V(133.15000,2.57000,0.03000),V(133.16500,2.72600,0.03000),V(133.21100,2.87600,0.03000),V(133.28500,3.01400,0.03000),V(133.38400,3.13600,0.03000),V(133.50600,3.23500,0.03000),V(133.64400,3.30900,0.03000),V(133.79400,3.35500,0.03000),V(133.95000,3.37000,0.03000),V(134.10600,3.35500,0.03000),V(134.25600,3.30900,0.03000),V(134.39400,3.23500,0.03000),V(134.51600,3.13600,0.03000),V(134.61500,3.01400,0.03000),V(134.68900,2.87600,0.03000),V(134.73500,2.72600,0.03000),V(134.75000,2.57000,0.03000),V(134.73500,2.41400,0.03000),V(134.68900,2.26400,0.03000),V(134.61500,2.12600,0.03000),V(134.51600,2.00400,0.03000),V(134.39400,1.90500,0.03000),V(134.25600,1.83100,0.03000),V(134.10600,1.78500,0.03000)])]).extrude(V(0,0,0.01000)))
_s.append(Part.Face([_poly([V(126.48600,1.78500,0.03000),V(126.33000,1.77000,0.03000),V(126.17400,1.78500,0.03000),V(126.02400,1.83100,0.03000),V(125.88600,1.90500,0.03000),V(125.76400,2.00400,0.03000),V(125.66500,2.12600,0.03000),V(125.59100,2.26400,0.03000),V(125.54500,2.41400,0.03000),V(125.53000,2.57000,0.03000),V(125.54500,2.72600,0.03000),V(125.59100,2.87600,0.03000),V(125.66500,3.01400,0.03000),V(125.76400,3.13600,0.03000),V(125.88600,3.23500,0.03000),V(126.02400,3.30900,0.03000),V(126.17400,3.35500,0.03000),V(126.33000,3.37000,0.03000),V(126.48600,3.35500,0.03000),V(126.63600,3.30900,0.03000),V(126.77400,3.23500,0.03000),V(126.89600,3.13600,0.03000),V(126.99500,3.01400,0.03000),V(127.06900,2.87600,0.03000),V(127.11500,2.72600,0.03000),V(127.13000,2.57000,0.03000),V(127.11500,2.41400,0.03000),V(127.06900,2.26400,0.03000),V(126.99500,2.12600,0.03000),V(126.89600,2.00400,0.03000),V(126.77400,1.90500,0.03000),V(126.63600,1.83100,0.03000),V(126.48600,1.78500,0.03000)])]).extrude(V(0,0,0.01000)))
_s.append(Part.Face([_poly([V(136.49000,1.77000,0.03000),V(136.33400,1.78500,0.03000),V(136.18400,1.83100,0.03000),V(136.04600,1.90500,0.03000),V(135.92400,2.00400,0.03000),V(135.82500,2.12600,0.03000),V(135.75100,2.26400,0.03000),V(135.70500,2.41400,0.03000),V(135.69000,2.57000,0.03000),V(135.70500,2.72600,0.03000),V(135.75100,2.87600,0.03000),V(135.82500,3.01400,0.03000),V(135.92400,3.13600,0.03000),V(136.04600,3.23500,0.03000),V(136.18400,3.30900,0.03000),V(136.33400,3.35500,0.03000),V(136.49000,3.37000,0.03000),V(136.64600,3.35500,0.03000),V(136.79600,3.30900,0.03000),V(136.93400,3.23500,0.03000),V(137.05600,3.13600,0.03000),V(137.15500,3.01400,0.03000),V(137.22900,2.87600,0.03000),V(137.27500,2.72600,0.03000),V(137.29000,2.57000,0.03000),V(137.27500,2.41400,0.03000),V(137.22900,2.26400,0.03000),V(137.15500,2.12600,0.03000),V(137.05600,2.00400,0.03000),V(136.93400,1.90500,0.03000),V(136.79600,1.83100,0.03000),V(136.64600,1.78500,0.03000),V(136.49000,1.77000,0.03000)])]).extrude(V(0,0,0.01000)))
_s.append(Part.Face([_poly([V(139.03000,1.77000,0.03000),V(138.87400,1.78500,0.03000),V(138.72400,1.83100,0.03000),V(138.58600,1.90500,0.03000),V(138.46400,2.00400,0.03000),V(138.36500,2.12600,0.03000),V(138.29100,2.26400,0.03000),V(138.24500,2.41400,0.03000),V(138.23000,2.57000,0.03000),V(138.24500,2.72600,0.03000),V(138.29100,2.87600,0.03000),V(138.36500,3.01400,0.03000),V(138.46400,3.13600,0.03000),V(138.58600,3.23500,0.03000),V(138.72400,3.30900,0.03000),V(138.87400,3.35500,0.03000),V(139.03000,3.37000,0.03000),V(139.18600,3.35500,0.03000),V(139.33600,3.30900,0.03000),V(139.47400,3.23500,0.03000),V(139.59600,3.13600,0.03000),V(139.69500,3.01400,0.03000),V(139.76900,2.87600,0.03000),V(139.81500,2.72600,0.03000),V(139.83000,2.57000,0.03000),V(139.81500,2.41400,0.03000),V(139.76900,2.26400,0.03000),V(139.69500,2.12600,0.03000),V(139.59600,2.00400,0.03000),V(139.47400,1.90500,0.03000),V(139.33600,1.83100,0.03000),V(139.18600,1.78500,0.03000),V(139.03000,1.77000,0.03000)])]).extrude(V(0,0,0.01000)))
_s.append(Part.Face([_poly([V(121.25000,24.63000,0.03000),V(121.09400,24.64500,0.03000),V(120.94400,24.69100,0.03000),V(120.80600,24.76500,0.03000),V(120.68400,24.86400,0.03000),V(120.58500,24.98600,0.03000),V(120.51100,25.12400,0.03000),V(120.46500,25.27400,0.03000),V(120.45000,25.43000,0.03000),V(120.46500,25.58600,0.03000),V(120.51100,25.73600,0.03000),V(120.58500,25.87400,0.03000),V(120.68400,25.99600,0.03000),V(120.80600,26.09500,0.03000),V(120.94400,26.16900,0.03000),V(121.09400,26.21500,0.03000),V(121.25000,26.23000,0.03000),V(121.40600,26.21500,0.03000),V(121.55600,26.16900,0.03000),V(121.69400,26.09500,0.03000),V(121.81600,25.99600,0.03000),V(121.91500,25.87400,0.03000),V(121.98900,25.73600,0.03000),V(122.03500,25.58600,0.03000),V(122.05000,25.43000,0.03000),V(122.03500,25.27400,0.03000),V(121.98900,25.12400,0.03000),V(121.91500,24.98600,0.03000),V(121.81600,24.86400,0.03000),V(121.69400,24.76500,0.03000),V(121.55600,24.69100,0.03000),V(121.40600,24.64500,0.03000),V(121.25000,24.63000,0.03000)])]).extrude(V(0,0,0.01000)))
_s.append(Part.Face([_poly([V(123.94600,24.64500,0.03000),V(123.79000,24.63000,0.03000),V(123.63400,24.64500,0.03000),V(123.48400,24.69100,0.03000),V(123.34600,24.76500,0.03000),V(123.22400,24.86400,0.03000),V(123.12500,24.98600,0.03000),V(123.05100,25.12400,0.03000),V(123.00500,25.27400,0.03000),V(122.99000,25.43000,0.03000),V(123.00500,25.58600,0.03000),V(123.05100,25.73600,0.03000),V(123.12500,25.87400,0.03000),V(123.22400,25.99600,0.03000),V(123.34600,26.09500,0.03000),V(123.48400,26.16900,0.03000),V(123.63400,26.21500,0.03000),V(123.79000,26.23000,0.03000),V(123.94600,26.21500,0.03000),V(124.09600,26.16900,0.03000),V(124.23400,26.09500,0.03000),V(124.35600,25.99600,0.03000),V(124.45500,25.87400,0.03000),V(124.52900,25.73600,0.03000),V(124.57500,25.58600,0.03000),V(124.59000,25.43000,0.03000),V(124.57500,25.27400,0.03000),V(124.52900,25.12400,0.03000),V(124.45500,24.98600,0.03000),V(124.35600,24.86400,0.03000),V(124.23400,24.76500,0.03000),V(124.09600,24.69100,0.03000),V(123.94600,24.64500,0.03000)])]).extrude(V(0,0,0.01000)))
_s.append(Part.Face([_poly([V(126.48600,24.64500,0.03000),V(126.33000,24.63000,0.03000),V(126.17400,24.64500,0.03000),V(126.02400,24.69100,0.03000),V(125.88600,24.76500,0.03000),V(125.76400,24.86400,0.03000),V(125.66500,24.98600,0.03000),V(125.59100,25.12400,0.03000),V(125.54500,25.27400,0.03000),V(125.53000,25.43000,0.03000),V(125.54500,25.58600,0.03000),V(125.59100,25.73600,0.03000),V(125.66500,25.87400,0.03000),V(125.76400,25.99600,0.03000),V(125.88600,26.09500,0.03000),V(126.02400,26.16900,0.03000),V(126.17400,26.21500,0.03000),V(126.33000,26.23000,0.03000),V(126.48600,26.21500,0.03000),V(126.63600,26.16900,0.03000),V(126.77400,26.09500,0.03000),V(126.89600,25.99600,0.03000),V(126.99500,25.87400,0.03000),V(127.06900,25.73600,0.03000),V(127.11500,25.58600,0.03000),V(127.13000,25.43000,0.03000),V(127.11500,25.27400,0.03000),V(127.06900,25.12400,0.03000),V(126.99500,24.98600,0.03000),V(126.89600,24.86400,0.03000),V(126.77400,24.76500,0.03000),V(126.63600,24.69100,0.03000),V(126.48600,24.64500,0.03000)])]).extrude(V(0,0,0.01000)))
_s.append(Part.Face([_poly([V(128.87000,24.63000,0.03000),V(128.71400,24.64500,0.03000),V(128.56400,24.69100,0.03000),V(128.42600,24.76500,0.03000),V(128.30400,24.86400,0.03000),V(128.20500,24.98600,0.03000),V(128.13100,25.12400,0.03000),V(128.08500,25.27400,0.03000),V(128.07000,25.43000,0.03000),V(128.08500,25.58600,0.03000),V(128.13100,25.73600,0.03000),V(128.20500,25.87400,0.03000),V(128.30400,25.99600,0.03000),V(128.42600,26.09500,0.03000),V(128.56400,26.16900,0.03000),V(128.71400,26.21500,0.03000),V(128.87000,26.23000,0.03000),V(129.02600,26.21500,0.03000),V(129.17600,26.16900,0.03000),V(129.31400,26.09500,0.03000),V(129.43600,25.99600,0.03000),V(129.53500,25.87400,0.03000),V(129.60900,25.73600,0.03000),V(129.65500,25.58600,0.03000),V(129.67000,25.43000,0.03000),V(129.65500,25.27400,0.03000),V(129.60900,25.12400,0.03000),V(129.53500,24.98600,0.03000),V(129.43600,24.86400,0.03000),V(129.31400,24.76500,0.03000),V(129.17600,24.69100,0.03000),V(129.02600,24.64500,0.03000),V(128.87000,24.63000,0.03000)])]).extrude(V(0,0,0.01000)))
_s.append(Part.Face([_poly([V(133.95000,24.63000,0.03000),V(133.79400,24.64500,0.03000),V(133.64400,24.69100,0.03000),V(133.50600,24.76500,0.03000),V(133.38400,24.86400,0.03000),V(133.28500,24.98600,0.03000),V(133.21100,25.12400,0.03000),V(133.16500,25.27400,0.03000),V(133.15000,25.43000,0.03000),V(133.16500,25.58600,0.03000),V(133.21100,25.73600,0.03000),V(133.28500,25.87400,0.03000),V(133.38400,25.99600,0.03000),V(133.50600,26.09500,0.03000),V(133.64400,26.16900,0.03000),V(133.79400,26.21500,0.03000),V(133.95000,26.23000,0.03000),V(134.10600,26.21500,0.03000),V(134.25600,26.16900,0.03000),V(134.39400,26.09500,0.03000),V(134.51600,25.99600,0.03000),V(134.61500,25.87400,0.03000),V(134.68900,25.73600,0.03000),V(134.73500,25.58600,0.03000),V(134.75000,25.43000,0.03000),V(134.73500,25.27400,0.03000),V(134.68900,25.12400,0.03000),V(134.61500,24.98600,0.03000),V(134.51600,24.86400,0.03000),V(134.39400,24.76500,0.03000),V(134.25600,24.69100,0.03000),V(134.10600,24.64500,0.03000),V(133.95000,24.63000,0.03000)])]).extrude(V(0,0,0.01000)))
_s.append(Part.Face([_poly([V(136.49000,24.63000,0.03000),V(136.33400,24.64500,0.03000),V(136.18400,24.69100,0.03000),V(136.04600,24.76500,0.03000),V(135.92400,24.86400,0.03000),V(135.82500,24.98600,0.03000),V(135.75100,25.12400,0.03000),V(135.70500,25.27400,0.03000),V(135.69000,25.43000,0.03000),V(135.70500,25.58600,0.03000),V(135.75100,25.73600,0.03000),V(135.82500,25.87400,0.03000),V(135.92400,25.99600,0.03000),V(136.04600,26.09500,0.03000),V(136.18400,26.16900,0.03000),V(136.33400,26.21500,0.03000),V(136.49000,26.23000,0.03000),V(136.64600,26.21500,0.03000),V(136.79600,26.16900,0.03000),V(136.93400,26.09500,0.03000),V(137.05600,25.99600,0.03000),V(137.15500,25.87400,0.03000),V(137.22900,25.73600,0.03000),V(137.27500,25.58600,0.03000),V(137.29000,25.43000,0.03000),V(137.27500,25.27400,0.03000),V(137.22900,25.12400,0.03000),V(137.15500,24.98600,0.03000),V(137.05600,24.86400,0.03000),V(136.93400,24.76500,0.03000),V(136.79600,24.69100,0.03000),V(136.64600,24.64500,0.03000),V(136.49000,24.63000,0.03000)])]).extrude(V(0,0,0.01000)))
_s.append(Part.Face([_poly([V(139.18600,24.64500,0.03000),V(139.03000,24.63000,0.03000),V(138.87400,24.64500,0.03000),V(138.72400,24.69100,0.03000),V(138.58600,24.76500,0.03000),V(138.46400,24.86400,0.03000),V(138.36500,24.98600,0.03000),V(138.29100,25.12400,0.03000),V(138.24500,25.27400,0.03000),V(138.23000,25.43000,0.03000),V(138.24500,25.58600,0.03000),V(138.29100,25.73600,0.03000),V(138.36500,25.87400,0.03000),V(138.46400,25.99600,0.03000),V(138.58600,26.09500,0.03000),V(138.72400,26.16900,0.03000),V(138.87400,26.21500,0.03000),V(139.03000,26.23000,0.03000),V(139.18600,26.21500,0.03000),V(139.33600,26.16900,0.03000),V(139.47400,26.09500,0.03000),V(139.59600,25.99600,0.03000),V(139.69500,25.87400,0.03000),V(139.76900,25.73600,0.03000),V(139.81500,25.58600,0.03000),V(139.83000,25.43000,0.03000),V(139.81500,25.27400,0.03000),V(139.76900,25.12400,0.03000),V(139.69500,24.98600,0.03000),V(139.59600,24.86400,0.03000),V(139.47400,24.76500,0.03000),V(139.33600,24.69100,0.03000),V(139.18600,24.64500,0.03000)])]).extrude(V(0,0,0.01000)))
_s.append(Part.Face([_poly([V(131.41000,24.63000,0.03000),V(131.25400,24.64500,0.03000),V(131.10400,24.69100,0.03000),V(130.96600,24.76500,0.03000),V(130.84400,24.86400,0.03000),V(130.74500,24.98600,0.03000),V(130.67100,25.12400,0.03000),V(130.62500,25.27400,0.03000),V(130.61000,25.43000,0.03000),V(130.62500,25.58600,0.03000),V(130.67100,25.73600,0.03000),V(130.74500,25.87400,0.03000),V(130.84400,25.99600,0.03000),V(130.96600,26.09500,0.03000),V(131.10400,26.16900,0.03000),V(131.25400,26.21500,0.03000),V(131.41000,26.23000,0.03000),V(131.56600,26.21500,0.03000),V(131.71600,26.16900,0.03000),V(131.85400,26.09500,0.03000),V(131.97600,25.99600,0.03000),V(132.07500,25.87400,0.03000),V(132.14900,25.73600,0.03000),V(132.19500,25.58600,0.03000),V(132.21000,25.43000,0.03000),V(132.19500,25.27400,0.03000),V(132.14900,25.12400,0.03000),V(132.07500,24.98600,0.03000),V(131.97600,24.86400,0.03000),V(131.85400,24.76500,0.03000),V(131.71600,24.69100,0.03000),V(131.56600,24.64500,0.03000),V(131.41000,24.63000,0.03000)])]).extrude(V(0,0,0.01000)))
_s.append(Part.Face([_poly([V(118.71000,24.63000,0.03000),V(118.55400,24.64500,0.03000),V(118.40400,24.69100,0.03000),V(118.26600,24.76500,0.03000),V(118.14400,24.86400,0.03000),V(118.04500,24.98600,0.03000),V(117.97100,25.12400,0.03000),V(117.92500,25.27400,0.03000),V(117.91000,25.43000,0.03000),V(117.92500,25.58600,0.03000),V(117.97100,25.73600,0.03000),V(118.04500,25.87400,0.03000),V(118.14400,25.99600,0.03000),V(118.26600,26.09500,0.03000),V(118.40400,26.16900,0.03000),V(118.55400,26.21500,0.03000),V(118.71000,26.23000,0.03000),V(118.86600,26.21500,0.03000),V(119.01600,26.16900,0.03000),V(119.15400,26.09500,0.03000),V(119.27600,25.99600,0.03000),V(119.37500,25.87400,0.03000),V(119.44900,25.73600,0.03000),V(119.49500,25.58600,0.03000),V(119.51000,25.43000,0.03000),V(119.49500,25.27400,0.03000),V(119.44900,25.12400,0.03000),V(119.37500,24.98600,0.03000),V(119.27600,24.86400,0.03000),V(119.15400,24.76500,0.03000),V(119.01600,24.69100,0.03000),V(118.86600,24.64500,0.03000),V(118.71000,24.63000,0.03000)])]).extrude(V(0,0,0.01000)))
_add('L63' + '_L63', _fuse(_s), (0.6667,1.0000,0.7647), surface=True)

_doc.recompute()
if _GUI:
    try:
        FreeCADGui.activeDocument().activeView().viewIsometric()
        FreeCADGui.SendMsgToActiveView("ViewFit")
    except Exception:
        pass
